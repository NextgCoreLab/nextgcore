-- **************************************************************
--
-- Elementary Procedure definitions
--
-- **************************************************************

NRPPA-PDU-Descriptions {
itu-t (0) identified-organization (4) etsi (0) mobileDomain (0)
ngran-access (22) modules (3) nrppa (4) version1 (1) nrppa-PDU-Descriptions (0) }

DEFINITIONS AUTOMATIC TAGS ::= 

BEGIN

-- **************************************************************
--
-- IE parameter types from other modules.
--
-- **************************************************************

IMPORTS
	Criticality,
	ProcedureCode,
	NRPPATransactionID

FROM NRPPA-CommonDataTypes


	ErrorIndication,
	PrivateMessage,
	E-CIDMeasurementInitiationRequest,
	E-CIDMeasurementInitiationResponse,
	E-CIDMeasurementInitiationFailure,
	E-CIDMeasurementFailureIndication,
	E-CIDMeasurementReport,
	E-CIDMeasurementTerminationCommand,
	OTDOAInformationRequest,
	OTDOAInformationResponse,
	OTDOAInformationFailure,
	AssistanceInformationControl,
	AssistanceInformationFeedback,
	PositioningInformationRequest,
	PositioningInformationResponse,
	PositioningInformationFailure,
	PositioningInformationUpdate,
	MeasurementRequest,
	MeasurementResponse,
	MeasurementFailure,
	MeasurementReport,
	MeasurementUpdate,
	MeasurementAbort,
	MeasurementFailureIndication,
	TRPInformationRequest,
	TRPInformationResponse,
	TRPInformationFailure,
	PositioningActivationRequest,
	PositioningActivationResponse,
	PositioningActivationFailure,
	PositioningDeactivation,
	PRSConfigurationRequest,
	PRSConfigurationResponse,
	PRSConfigurationFailure,
	MeasurementPreconfigurationRequired,
	MeasurementPreconfigurationConfirm,
	MeasurementPreconfigurationRefuse,
	MeasurementActivation,
	SRSInformationReservationNotification,
	PositioningDataCollectionReport


FROM NRPPA-PDU-Contents

	id-errorIndication,
	id-privateMessage,
	id-e-CIDMeasurementInitiation,
	id-e-CIDMeasurementFailureIndication,
	id-e-CIDMeasurementReport,
	id-e-CIDMeasurementTermination,
	id-oTDOAInformationExchange,
	id-assistanceInformationControl,
	id-assistanceInformationFeedback,
	id-positioningInformationExchange,
	id-positioningInformationUpdate,
	id-Measurement,
	id-MeasurementReport,
	id-MeasurementUpdate,
	id-MeasurementAbort,
	id-MeasurementFailureIndication,
	id-tRPInformationExchange, 
	id-positioningActivation,
	id-positioningDeactivation,
	id-pRSConfigurationExchange,
	id-measurementPreconfiguration,
	id-measurementActivation,
	id-sRSInformationReservationNotification,
	id-positioningDataCollectionReport



FROM NRPPA-Constants;

-- **************************************************************
--
-- Interface Elementary Procedure Class
--
-- **************************************************************

NRPPA-ELEMENTARY-PROCEDURE ::= CLASS {
	&InitiatingMessage				,
	&SuccessfulOutcome							OPTIONAL,
	&UnsuccessfulOutcome						OPTIONAL,
	&procedureCode				ProcedureCode	UNIQUE,
	&criticality				Criticality	DEFAULT ignore
}
WITH SYNTAX {
	INITIATING MESSAGE			&InitiatingMessage
	[SUCCESSFUL OUTCOME		&SuccessfulOutcome]
	[UNSUCCESSFUL OUTCOME		&UnsuccessfulOutcome]
	PROCEDURE CODE				&procedureCode
	[CRITICALITY				&criticality]
}

-- **************************************************************
--
-- Interface PDU Definition
--
-- **************************************************************

NRPPA-PDU ::= CHOICE {
	initiatingMessage		InitiatingMessage,
	successfulOutcome		SuccessfulOutcome,
	unsuccessfulOutcome	UnsuccessfulOutcome,
	...
}

InitiatingMessage ::= SEQUENCE {
	procedureCode			NRPPA-ELEMENTARY-PROCEDURE.&procedureCode		({NRPPA-ELEMENTARY-PROCEDURES}),
	criticality			NRPPA-ELEMENTARY-PROCEDURE.&criticality			({NRPPA-ELEMENTARY-PROCEDURES}{@procedureCode}),
	nrppatransactionID		NRPPATransactionID,
	value					NRPPA-ELEMENTARY-PROCEDURE.&InitiatingMessage	({NRPPA-ELEMENTARY-PROCEDURES}{@procedureCode})
}

SuccessfulOutcome ::= SEQUENCE {
	procedureCode			NRPPA-ELEMENTARY-PROCEDURE.&procedureCode		({NRPPA-ELEMENTARY-PROCEDURES}),
	criticality			NRPPA-ELEMENTARY-PROCEDURE.&criticality			({NRPPA-ELEMENTARY-PROCEDURES}{@procedureCode}),
	nrppatransactionID		NRPPATransactionID,
	value					NRPPA-ELEMENTARY-PROCEDURE.&SuccessfulOutcome	({NRPPA-ELEMENTARY-PROCEDURES}{@procedureCode})
}

UnsuccessfulOutcome ::= SEQUENCE {
	procedureCode			NRPPA-ELEMENTARY-PROCEDURE.&procedureCode		({NRPPA-ELEMENTARY-PROCEDURES}),
	criticality			NRPPA-ELEMENTARY-PROCEDURE.&criticality			({NRPPA-ELEMENTARY-PROCEDURES}{@procedureCode}),
	nrppatransactionID		NRPPATransactionID,
	value					NRPPA-ELEMENTARY-PROCEDURE.&UnsuccessfulOutcome	({NRPPA-ELEMENTARY-PROCEDURES}{@procedureCode})
}


-- **************************************************************
--
-- Interface Elementary Procedure List
--
-- **************************************************************

NRPPA-ELEMENTARY-PROCEDURES NRPPA-ELEMENTARY-PROCEDURE ::= {
	NRPPA-ELEMENTARY-PROCEDURES-CLASS-1			|
	NRPPA-ELEMENTARY-PROCEDURES-CLASS-2			,
	...
}

NRPPA-ELEMENTARY-PROCEDURES-CLASS-1 NRPPA-ELEMENTARY-PROCEDURE ::= {
	e-CIDMeasurementInitiation	|
	oTDOAInformationExchange	|
	positioningInformationExchange	|
	measurement						|
	tRPInformationExchange		|
	positioningActivation		|
	pRSConfigurationExchange	|
	measurementPreconfiguration,

	...
}

NRPPA-ELEMENTARY-PROCEDURES-CLASS-2 NRPPA-ELEMENTARY-PROCEDURE ::= {
	e-CIDMeasurementFailureIndication		|
	e-CIDMeasurementReport					|
	e-CIDMeasurementTermination				|
	errorIndication							|
	privateMessage							|
	assistanceInformationControl			|
	assistanceInformationFeedback 			|
	positioningInformationUpdate			|
	measurementReport						|
	measurementUpdate						|
	measurementAbort						|
	measurementFailureIndication		|
	positioningDeactivation		|
	measurementActivation					|
	sRSInformationReservationNotification	|
	positioningDataCollectionReport,
	...
}


-- **************************************************************
--
-- Interface Elementary Procedures
--
-- **************************************************************

e-CIDMeasurementInitiation NRPPA-ELEMENTARY-PROCEDURE ::= {
	INITIATING MESSAGE		E-CIDMeasurementInitiationRequest
	SUCCESSFUL OUTCOME		E-CIDMeasurementInitiationResponse
	UNSUCCESSFUL OUTCOME	E-CIDMeasurementInitiationFailure
	PROCEDURE CODE			id-e-CIDMeasurementInitiation
	CRITICALITY				reject
}

e-CIDMeasurementFailureIndication NRPPA-ELEMENTARY-PROCEDURE ::= {
	INITIATING MESSAGE		E-CIDMeasurementFailureIndication
	PROCEDURE CODE			id-e-CIDMeasurementFailureIndication
	CRITICALITY				ignore
}

e-CIDMeasurementReport NRPPA-ELEMENTARY-PROCEDURE ::= {
	INITIATING MESSAGE		E-CIDMeasurementReport
	PROCEDURE CODE			id-e-CIDMeasurementReport
	CRITICALITY				ignore
}

e-CIDMeasurementTermination NRPPA-ELEMENTARY-PROCEDURE ::= {
	INITIATING MESSAGE		E-CIDMeasurementTerminationCommand
	PROCEDURE CODE			id-e-CIDMeasurementTermination
	CRITICALITY				reject
}

oTDOAInformationExchange NRPPA-ELEMENTARY-PROCEDURE ::= {
	INITIATING MESSAGE		OTDOAInformationRequest
	SUCCESSFUL OUTCOME		OTDOAInformationResponse
	UNSUCCESSFUL OUTCOME	OTDOAInformationFailure
	PROCEDURE CODE			id-oTDOAInformationExchange
	CRITICALITY				reject
}


assistanceInformationControl NRPPA-ELEMENTARY-PROCEDURE ::= {
	INITIATING MESSAGE		AssistanceInformationControl
	PROCEDURE CODE			id-assistanceInformationControl
	CRITICALITY				reject
}

assistanceInformationFeedback NRPPA-ELEMENTARY-PROCEDURE ::= {
	INITIATING MESSAGE		AssistanceInformationFeedback
	PROCEDURE CODE			id-assistanceInformationFeedback
	CRITICALITY				reject
}


errorIndication NRPPA-ELEMENTARY-PROCEDURE ::= {
	INITIATING MESSAGE		ErrorIndication
	PROCEDURE CODE			id-errorIndication
	CRITICALITY			ignore
}


privateMessage			NRPPA-ELEMENTARY-PROCEDURE ::= {
	INITIATING MESSAGE		PrivateMessage
	PROCEDURE CODE			id-privateMessage
	CRITICALITY			ignore
}


positioningInformationExchange	NRPPA-ELEMENTARY-PROCEDURE ::= {
	INITIATING MESSAGE		PositioningInformationRequest
	SUCCESSFUL OUTCOME		PositioningInformationResponse
	UNSUCCESSFUL OUTCOME	PositioningInformationFailure
	PROCEDURE CODE			id-positioningInformationExchange
	CRITICALITY				reject
}

positioningInformationUpdate	NRPPA-ELEMENTARY-PROCEDURE ::= {
	INITIATING MESSAGE		PositioningInformationUpdate
	PROCEDURE CODE			id-positioningInformationUpdate
	CRITICALITY				ignore
}

measurement	NRPPA-ELEMENTARY-PROCEDURE ::= {
	INITIATING MESSAGE		MeasurementRequest
	SUCCESSFUL OUTCOME		MeasurementResponse
	UNSUCCESSFUL OUTCOME	MeasurementFailure
	PROCEDURE CODE			id-Measurement
	CRITICALITY				reject
}

measurementReport	NRPPA-ELEMENTARY-PROCEDURE ::= {
	INITIATING MESSAGE		MeasurementReport
	PROCEDURE CODE			id-MeasurementReport
	CRITICALITY				ignore
}

measurementUpdate	NRPPA-ELEMENTARY-PROCEDURE ::= {
	INITIATING MESSAGE		MeasurementUpdate
	PROCEDURE CODE			id-MeasurementUpdate
	CRITICALITY				ignore
}

measurementAbort	NRPPA-ELEMENTARY-PROCEDURE ::= {
	INITIATING MESSAGE		MeasurementAbort
	PROCEDURE CODE			id-MeasurementAbort
	CRITICALITY				ignore
}

measurementFailureIndication	NRPPA-ELEMENTARY-PROCEDURE ::= {
	INITIATING MESSAGE		MeasurementFailureIndication
	PROCEDURE CODE			id-MeasurementFailureIndication
	CRITICALITY				ignore
}

tRPInformationExchange	NRPPA-ELEMENTARY-PROCEDURE ::= {
	INITIATING MESSAGE		TRPInformationRequest
	SUCCESSFUL OUTCOME		TRPInformationResponse
	UNSUCCESSFUL OUTCOME	TRPInformationFailure
	PROCEDURE CODE			id-tRPInformationExchange
	CRITICALITY				reject
}

positioningActivation NRPPA-ELEMENTARY-PROCEDURE ::= {
	INITIATING MESSAGE		PositioningActivationRequest
	SUCCESSFUL OUTCOME		PositioningActivationResponse
	UNSUCCESSFUL OUTCOME	PositioningActivationFailure
	PROCEDURE CODE			id-positioningActivation
	CRITICALITY				reject
}

positioningDeactivation NRPPA-ELEMENTARY-PROCEDURE ::= {
	INITIATING MESSAGE		PositioningDeactivation
	PROCEDURE CODE			id-positioningDeactivation
	CRITICALITY				ignore
}

pRSConfigurationExchange NRPPA-ELEMENTARY-PROCEDURE ::= {
	INITIATING MESSAGE		PRSConfigurationRequest
	SUCCESSFUL OUTCOME		PRSConfigurationResponse
	UNSUCCESSFUL OUTCOME	PRSConfigurationFailure
	PROCEDURE CODE			id-pRSConfigurationExchange
	CRITICALITY				reject
}

measurementPreconfiguration NRPPA-ELEMENTARY-PROCEDURE ::= {
	INITIATING MESSAGE		MeasurementPreconfigurationRequired
	SUCCESSFUL OUTCOME		MeasurementPreconfigurationConfirm
	UNSUCCESSFUL OUTCOME		MeasurementPreconfigurationRefuse
	PROCEDURE CODE			id-measurementPreconfiguration
	CRITICALITY				reject
}

measurementActivation NRPPA-ELEMENTARY-PROCEDURE ::= {
	INITIATING MESSAGE		MeasurementActivation
	PROCEDURE CODE			id-measurementActivation
	CRITICALITY				ignore
}

sRSInformationReservationNotification NRPPA-ELEMENTARY-PROCEDURE ::= {
	INITIATING MESSAGE		SRSInformationReservationNotification
	PROCEDURE CODE			id-sRSInformationReservationNotification
	CRITICALITY				reject
}

positioningDataCollectionReport NRPPA-ELEMENTARY-PROCEDURE ::= {
	INITIATING MESSAGE		PositioningDataCollectionReport
	PROCEDURE CODE			id-positioningDataCollectionReport
	CRITICALITY				reject
}



END

-- **************************************************************
--
-- PDU definitions for NRPPa
--
-- **************************************************************

NRPPA-PDU-Contents {
itu-t (0) identified-organization (4) etsi (0) mobileDomain (0) 
ngran-access (22) modules (3) nrppa (4) version1 (1) nrppa-PDU-Contents (1) }

DEFINITIONS AUTOMATIC TAGS ::= 

BEGIN

-- **************************************************************
--
-- IE parameter types from other modules
--
-- **************************************************************

IMPORTS
	
	Cause,
	CriticalityDiagnostics,
	E-CID-MeasurementResult,
	OTDOACells,
	OTDOA-Information-Item,
	Measurement-ID,
	UE-Measurement-ID,
	MeasurementPeriodicity,
	MeasurementQuantities,
	ReportCharacteristics,
	RequestedSRSTransmissionCharacteristics,
	Cell-Portion-ID,
	OtherRATMeasurementQuantities,
	OtherRATMeasurementResult,
	WLANMeasurementQuantities,
	WLANMeasurementResult,
	Assistance-Information,
	Broadcast,
	AssistanceInformationFailureList,
	SRSConfiguration,
	TRPMeasurementQuantities,
	TrpMeasurementResult,
	TRP-ID,
		TRPInformationTypeListTRPReq,
		TRPInformationListTRPResp,
		TRP-MeasurementRequestList,
		TRP-MeasurementResponseList,
	TRP-MeasurementUpdateList,
		MeasurementBeamInfoRequest,
		PositioningBroadcastCells,
		SRSResourceSetID,
		SpatialRelationInfo,
		SRSResourceTrigger,
		TRPList,
		AbortTransmission,
		SystemFrameNumber,
		SlotNumber,
	RelativeTime1900,
		SpatialRelationPerSRSResource,
		MeasurementPeriodicityExtended,
	PRSTRPList,
	PRSTransmissionTRPList,
	ResponseTime,
	UEReportingInformation,
	UETxTEGAssociationList,
	TRP-PRS-Information-List,
	PRS-Measurements-Info-List,
	UE-TEG-Info-Request,
	MeasurementCharacteristicsRequestIndicator,
	MeasurementTimeOccasion,
	PRSConfigRequestType,
	MeasurementAmount,
	PreconfigurationResult,
	RequestType,
	UE-TEG-ReportingPeriodicity,
	MeasurementPeriodicityNR-AoA,
	SRSTransmissionStatus,
	CGI-NR,
	TimeWindowInformation-SRS-List,
	TimeWindowInformation-Measurement-List,
	PosValidityAreaCellList,
	SRSReservationType,
	RequestedSRSPreconfigurationCharacteristics-List,
	SRSPreconfiguration-List,
	PosSRSResourceSet-Aggregation-List,
	Remote-UE-Indication-Request,
	Remote-UE-Indication, 
	Remote-UE-Status,
	PositioningDataInformation,
	PositioningDataUnavailable,
	PositioningDataCollectionNeeded



	
FROM NRPPA-IEs

	PrivateIE-Container{},
	ProtocolExtensionContainer{},
	ProtocolIE-Container{},
	ProtocolIE-ContainerList{},
	ProtocolIE-Single-Container{},
	NRPPA-PRIVATE-IES,
	NRPPA-PROTOCOL-EXTENSION,
	NRPPA-PROTOCOL-IES
FROM NRPPA-Containers

	
	maxnoOTDOAtypes,
	id-Cause,
	id-CriticalityDiagnostics,
	id-LMF-Measurement-ID,
	id-LMF-UE-Measurement-ID,
	id-OTDOACells,
	id-OTDOA-Information-Type-Group,
	id-OTDOA-Information-Type-Item,
		id-ReportCharacteristics,
		id-MeasurementPeriodicity,
		id-MeasurementQuantities,
		id-RAN-Measurement-ID,
		id-RAN-UE-Measurement-ID,
		id-E-CID-MeasurementResult,
		id-RequestedSRSTransmissionCharacteristics,
		id-Cell-Portion-ID,
		id-OtherRATMeasurementQuantities,
		id-OtherRATMeasurementResult,
		id-WLANMeasurementQuantities,
		id-WLANMeasurementResult,
		id-Assistance-Information,
		id-Broadcast,
		id-AssistanceInformationFailureList,
		id-SRSConfiguration,
	id-TRPMeasurementQuantities,
	id-MeasurementResult,
	id-TRP-ID,
		id-TRPInformationTypeListTRPReq,
		id-TRPInformationListTRPResp,
		id-TRP-MeasurementRequestList,
		id-TRP-MeasurementResponseList,
		id-TRP-MeasurementReportList,
	id-TRP-MeasurementUpdateList,
		id-MeasurementBeamInfoRequest,
		id-PositioningBroadcastCells,
		id-SRSType,
		id-ActivationTime,
		id-SRSResourceSetID,
		id-TRPList,
		id-SRSSpatialRelation,
		id-AbortTransmission, 
		id-SystemFrameNumber,
		id-SlotNumber,
		id-SRSResourceTrigger,
		id-SFNInitialisationTime,
		id-SRSSpatialRelationPerSRSResource,
		id-MeasurementPeriodicityExtended,
	id-PRSTRPList,
	id-PRSTransmissionTRPList,
	id-ResponseTime,
	id-UEReportingInformation,
	id-UETxTEGAssociationList,
	id-TRP-PRS-Information-List,
	id-PRS-Measurements-Info-List,
	id-UE-TEG-Info-Request,
	id-MeasurementCharacteristicsRequestIndicator,
	id-MeasurementTimeOccasion,
	id-PRSConfigRequestType,
	id-MeasurementAmount,
	id-PreconfigurationResult,
	id-RequestType,
	id-UE-TEG-ReportingPeriodicity,
	id-MeasurementPeriodicityNR-AoA,
	id-SRSTransmissionStatus,
	id-NewNRCGI,
	id-TimeWindowInformation-SRS-List,
	id-TimeWindowInformation-Measurement-List,
	id-PosValidityAreaCellList,
	id-SRSReservationType,
	id-NewCellIdentity,
	id-RequestedSRSPreconfigurationCharacteristics-List,
	id-SRSPreconfiguration-List,
	id-SRSInformation,
	id-PosSRSResourceSet-Aggregation-List,
	id-PreconfiguredSRSInformation,
	id-Remote-UE-Indication-Request,
	id-Remote-UE-Indication,
	id-Remote-UE-Status,
	id-PositioningDataInformation,
	id-PositioningDataUnavailable


	
	
		
FROM NRPPA-Constants;

-- **************************************************************
--
-- E-CID MEASUREMENT INITIATION REQUEST
--
-- **************************************************************
	
	E-CIDMeasurementInitiationRequest ::= SEQUENCE {
		protocolIEs		ProtocolIE-Container	{{E-CIDMeasurementInitiationRequest-IEs}},
		...
	}
	
	E-CIDMeasurementInitiationRequest-IEs NRPPA-PROTOCOL-IES ::= {
		{ ID id-LMF-UE-Measurement-ID			CRITICALITY reject	TYPE UE-Measurement-ID					PRESENCE mandatory}|
		{ ID id-ReportCharacteristics			CRITICALITY reject	TYPE ReportCharacteristics				PRESENCE mandatory}|
		{ ID id-MeasurementPeriodicity			CRITICALITY reject	TYPE MeasurementPeriodicity				PRESENCE conditional}|
	-- The IE shall be present if the Report Characteritics IE is set to the value “periodic” --
		{ ID id-MeasurementQuantities			CRITICALITY reject	TYPE MeasurementQuantities				PRESENCE mandatory}|
		{ ID id-OtherRATMeasurementQuantities	CRITICALITY ignore	TYPE OtherRATMeasurementQuantities		PRESENCE optional}|
		{ ID id-WLANMeasurementQuantities		CRITICALITY ignore	TYPE WLANMeasurementQuantities			PRESENCE optional}|
		{ ID id-MeasurementPeriodicityNR-AoA	CRITICALITY reject	TYPE MeasurementPeriodicityNR-AoA		PRESENCE conditional},
	-- The IE shall be present if the Report Characteritics IE is set to the value “periodic” and the Measurement Quantities Value IE in the Measurement Quantities IE is set to the value "NR Angle of Arrival" --
		...
	}
	
-- **************************************************************
--
-- E-CID MEASUREMENT INITIATION RESPONSE
--
-- **************************************************************
	
	E-CIDMeasurementInitiationResponse ::= SEQUENCE {
		protocolIEs		ProtocolIE-Container	{{E-CIDMeasurementInitiationResponse-IEs}},
		...
	}
	
	E-CIDMeasurementInitiationResponse-IEs NRPPA-PROTOCOL-IES ::= {
		{ ID id-LMF-UE-Measurement-ID		CRITICALITY reject	TYPE UE-Measurement-ID					PRESENCE mandatory}|
		{ ID id-RAN-UE-Measurement-ID		CRITICALITY reject	TYPE UE-Measurement-ID					PRESENCE mandatory}|
		{ ID id-E-CID-MeasurementResult		CRITICALITY ignore	TYPE E-CID-MeasurementResult			PRESENCE optional}|
		{ ID id-CriticalityDiagnostics		CRITICALITY ignore	TYPE CriticalityDiagnostics			PRESENCE optional}|
		{ ID id-Cell-Portion-ID				CRITICALITY ignore	TYPE Cell-Portion-ID					PRESENCE optional}|
		{ ID id-OtherRATMeasurementResult	CRITICALITY ignore	TYPE OtherRATMeasurementResult		PRESENCE optional}|
		{ ID id-WLANMeasurementResult		CRITICALITY ignore	TYPE WLANMeasurementResult			PRESENCE optional},
		...
	}
	
-- **************************************************************
--
-- E-CID MEASUREMENT INITIATION FAILURE
--
-- **************************************************************

	E-CIDMeasurementInitiationFailure ::= SEQUENCE {
		protocolIEs						ProtocolIE-Container		{{E-CIDMeasurementInitiationFailure-IEs}},
		...
	}
	
	
	E-CIDMeasurementInitiationFailure-IEs NRPPA-PROTOCOL-IES ::= {
		{ ID id-LMF-UE-Measurement-ID		CRITICALITY reject	TYPE UE-Measurement-ID				PRESENCE mandatory}|
		{ ID id-Cause							CRITICALITY ignore	TYPE Cause							PRESENCE mandatory}|
	{ ID id-CriticalityDiagnostics		CRITICALITY ignore	TYPE CriticalityDiagnostics		PRESENCE optional},
	...
}

-- **************************************************************
--
-- E-CID MEASUREMENT FAILURE INDICATION
--
-- **************************************************************

E-CIDMeasurementFailureIndication ::= SEQUENCE {
	protocolIEs						ProtocolIE-Container		{{E-CIDMeasurementFailureIndication-IEs}},
	...
	}
	
	
	E-CIDMeasurementFailureIndication-IEs NRPPA-PROTOCOL-IES ::= {
		{ ID id-LMF-UE-Measurement-ID		CRITICALITY reject	TYPE UE-Measurement-ID				PRESENCE mandatory}|
		{ ID id-RAN-UE-Measurement-ID		CRITICALITY reject	TYPE UE-Measurement-ID				PRESENCE mandatory}|
		{ ID id-Cause							CRITICALITY ignore	TYPE Cause							PRESENCE mandatory},
		...
	}

-- **************************************************************
--
-- E-CID MEASUREMENT REPORT
--
-- **************************************************************
	
	E-CIDMeasurementReport ::= SEQUENCE {
		protocolIEs						ProtocolIE-Container		{{E-CIDMeasurementReport-IEs}},
		...
	}
	
	
	E-CIDMeasurementReport-IEs NRPPA-PROTOCOL-IES ::= {
		{ ID id-LMF-UE-Measurement-ID		CRITICALITY reject	TYPE UE-Measurement-ID				PRESENCE mandatory}|
		{ ID id-RAN-UE-Measurement-ID		CRITICALITY reject	TYPE UE-Measurement-ID				PRESENCE mandatory}|
		{ ID id-E-CID-MeasurementResult		CRITICALITY ignore	TYPE E-CID-MeasurementResult		PRESENCE mandatory}|
		{ ID id-Cell-Portion-ID				CRITICALITY ignore	TYPE Cell-Portion-ID				PRESENCE optional},
		...
	}

-- **************************************************************
--
-- E-CID MEASUREMENT TERMINATION COMMAND
--
-- **************************************************************
	
	E-CIDMeasurementTerminationCommand ::= SEQUENCE {
		protocolIEs						ProtocolIE-Container		{{E-CIDMeasurementTerminationCommand-IEs}},
		...
	}
	
	
	E-CIDMeasurementTerminationCommand-IEs NRPPA-PROTOCOL-IES ::= {
		{ ID id-LMF-UE-Measurement-ID		CRITICALITY reject	TYPE UE-Measurement-ID				PRESENCE mandatory}|
		{ ID id-RAN-UE-Measurement-ID		CRITICALITY reject	TYPE UE-Measurement-ID				PRESENCE mandatory},
		...
	}

-- **************************************************************
--
-- OTDOA INFORMATION REQUEST
--
-- **************************************************************
	
	OTDOAInformationRequest ::= SEQUENCE {
		protocolIEs		ProtocolIE-Container	{{OTDOAInformationRequest-IEs}},
		...
	}
	
	OTDOAInformationRequest-IEs NRPPA-PROTOCOL-IES ::= {
		{ ID id-OTDOA-Information-Type-Group		CRITICALITY reject	TYPE OTDOA-Information-Type			PRESENCE mandatory},
		...
	}
	
	OTDOA-Information-Type ::= SEQUENCE (SIZE(1..maxnoOTDOAtypes)) OF ProtocolIE-Single-Container { { OTDOA-Information-Type-ItemIEs} }
	
	OTDOA-Information-Type-ItemIEs	NRPPA-PROTOCOL-IES ::= {
		{ ID id-OTDOA-Information-Type-Item		CRITICALITY reject	TYPE OTDOA-Information-Type-Item	PRESENCE mandatory},
		...
	}
	
	OTDOA-Information-Type-Item ::= SEQUENCE {
		oTDOA-Information-Item		OTDOA-Information-Item,
		iE-Extensions					ProtocolExtensionContainer { { OTDOA-Information-Type-ItemExtIEs} } OPTIONAL,
		...
	}
	
	OTDOA-Information-Type-ItemExtIEs NRPPA-PROTOCOL-EXTENSION ::= {
		...
	}

-- **************************************************************
--
-- OTDOA INFORMATION RESPONSE
--
-- **************************************************************
	
	OTDOAInformationResponse ::= SEQUENCE {
		protocolIEs		ProtocolIE-Container	{{OTDOAInformationResponse-IEs}},
		...
	}
	
	OTDOAInformationResponse-IEs NRPPA-PROTOCOL-IES ::= {
		{ ID id-OTDOACells						CRITICALITY ignore	TYPE OTDOACells					PRESENCE mandatory}|
		{ ID id-CriticalityDiagnostics			CRITICALITY ignore	TYPE CriticalityDiagnostics		PRESENCE optional},
		...
}

-- **************************************************************
--
-- OTDOA INFORMATION FAILURE
--
-- **************************************************************
	
	OTDOAInformationFailure ::= SEQUENCE {
		protocolIEs						ProtocolIE-Container		{{OTDOAInformationFailure-IEs}},
		...
	}
	
	
	OTDOAInformationFailure-IEs NRPPA-PROTOCOL-IES ::= {
		{ ID id-Cause							CRITICALITY ignore	TYPE Cause						PRESENCE mandatory}|
		{ ID id-CriticalityDiagnostics			CRITICALITY ignore	TYPE CriticalityDiagnostics		PRESENCE optional},
	...
}

-- **************************************************************
--
-- ASSISTANCE INFORMATION CONTROL
--
-- **************************************************************

AssistanceInformationControl ::= SEQUENCE {
	protocolIEs		ProtocolIE-Container	{{AssistanceInformationControl-IEs}},
	...
}

AssistanceInformationControl-IEs NRPPA-PROTOCOL-IES ::= {
	{ ID id-Assistance-Information	CRITICALITY reject	TYPE Assistance-Information		PRESENCE optional}|
	{ ID id-Broadcast				CRITICALITY reject	TYPE Broadcast					PRESENCE optional}|
	{ ID id-PositioningBroadcastCells				CRITICALITY reject	TYPE PositioningBroadcastCells					PRESENCE optional},
	...
}

-- **************************************************************
--
-- ASSISTANCE INFORMATION FEEDBACK
--
-- **************************************************************

AssistanceInformationFeedback ::= SEQUENCE {
	protocolIEs		ProtocolIE-Container	{{AssistanceInformationFeedback-IEs}},
	...
}

AssistanceInformationFeedback-IEs NRPPA-PROTOCOL-IES ::= {
	{ ID id-AssistanceInformationFailureList	CRITICALITY reject	TYPE AssistanceInformationFailureList	PRESENCE optional}|
	{ ID id-PositioningBroadcastCells				CRITICALITY reject	TYPE PositioningBroadcastCells					PRESENCE optional}|
	{ ID id-CriticalityDiagnostics				CRITICALITY ignore	TYPE CriticalityDiagnostics					PRESENCE optional},
	...
}
	
	
-- **************************************************************
--
-- ERROR INDICATION
--
-- **************************************************************

	ErrorIndication ::= SEQUENCE {
		protocolIEs		ProtocolIE-Container	{{ErrorIndication-IEs}},
		...
	}
	
	ErrorIndication-IEs NRPPA-PROTOCOL-IES ::= {
		
		{ ID id-Cause							CRITICALITY ignore	TYPE Cause						PRESENCE optional}|
		{ ID id-CriticalityDiagnostics		CRITICALITY ignore	TYPE CriticalityDiagnostics	PRESENCE optional},
		...
	}

-- **************************************************************
--
-- PRIVATE MESSAGE
--
-- **************************************************************
	
	PrivateMessage ::= SEQUENCE {
		privateIEs		PrivateIE-Container	{{PrivateMessage-IEs}},
		...
	}
	
	PrivateMessage-IEs NRPPA-PRIVATE-IES ::= {
		...
	}

-- **************************************************************
--
-- POSITIONING INFORMATION REQUEST
--
-- **************************************************************
	
	PositioningInformationRequest ::= SEQUENCE {
		protocolIEs		ProtocolIE-Container	{{PositioningInformationRequest-IEs}},
		...
	}
	
PositioningInformationRequest-IEs NRPPA-PROTOCOL-IES ::= {
	{ ID id-RequestedSRSTransmissionCharacteristics	CRITICALITY ignore	TYPE RequestedSRSTransmissionCharacteristics	PRESENCE optional	}|
	{ ID id-UEReportingInformation					CRITICALITY ignore	TYPE UEReportingInformation							PRESENCE optional	}|
	{ ID id-UE-TEG-Info-Request						CRITICALITY ignore	TYPE UE-TEG-Info-Request								PRESENCE optional	}|
	{ ID id-UE-TEG-ReportingPeriodicity				CRITICALITY reject	TYPE UE-TEG-ReportingPeriodicity					PRESENCE conditional	}|
	-- This IE shall be present if the UE TEG Information Request IE is set to the value "periodic".
	{ ID id-TimeWindowInformation-SRS-List			CRITICALITY ignore	TYPE TimeWindowInformation-SRS-List				PRESENCE optional	}|
	{ ID id-RequestedSRSPreconfigurationCharacteristics-List	CRITICALITY ignore	TYPE RequestedSRSPreconfigurationCharacteristics-List				PRESENCE optional	}|
		{ ID id-Remote-UE-Indication-Request			CRITICALITY ignore	TYPE Remote-UE-Indication-Request				PRESENCE optional	},
		...
	}
	
-- **************************************************************
--
-- POSITIONING INFORMATION RESPONSE
--
-- **************************************************************
	
	PositioningInformationResponse ::= SEQUENCE {
		protocolIEs		ProtocolIE-Container	{{PositioningInformationResponse-IEs}},
		...
	}
	
	PositioningInformationResponse-IEs NRPPA-PROTOCOL-IES ::= {
		{ ID id-SRSConfiguration			CRITICALITY ignore	TYPE SRSConfiguration				PRESENCE optional}|
		{ ID id-SFNInitialisationTime		CRITICALITY ignore	TYPE RelativeTime1900			PRESENCE optional}|
	{ ID id-CriticalityDiagnostics		CRITICALITY ignore	TYPE CriticalityDiagnostics		PRESENCE optional}|
	{ ID id-UETxTEGAssociationList		CRITICALITY ignore	TYPE UETxTEGAssociationList		PRESENCE optional}|
	{ ID id-NewNRCGI					CRITICALITY ignore	TYPE CGI-NR							PRESENCE optional}|
	{ ID id-PosValidityAreaCellList		CRITICALITY ignore	TYPE PosValidityAreaCellList	PRESENCE optional}|
	{ ID id-SRSPreconfiguration-List	CRITICALITY ignore	TYPE SRSPreconfiguration-List	PRESENCE optional}|
	{ ID id-Remote-UE-Indication		CRITICALITY ignore	TYPE Remote-UE-Indication			PRESENCE optional},
	...
	}

-- **************************************************************
--
-- POSITIONING INFORMATION FAILURE
--
-- **************************************************************
	
	PositioningInformationFailure ::= SEQUENCE {
		protocolIEs						ProtocolIE-Container		{{PositioningInformationFailure-IEs}},
		...
	}
	
	PositioningInformationFailure-IEs NRPPA-PROTOCOL-IES ::= {
		{ ID id-Cause						CRITICALITY ignore	TYPE Cause						PRESENCE mandatory}|
		{ ID id-CriticalityDiagnostics		CRITICALITY ignore	TYPE CriticalityDiagnostics		PRESENCE optional},
		...
	}
	
-- **************************************************************
--
-- POSITIONING INFORMATION UPDATE
--
-- **************************************************************
	
	PositioningInformationUpdate ::= SEQUENCE {
		protocolIEs		ProtocolIE-Container	{{PositioningInformationUpdate-IEs}},
		...
	}
	
	PositioningInformationUpdate-IEs NRPPA-PROTOCOL-IES ::= {
		{ ID id-SRSConfiguration			CRITICALITY ignore	TYPE SRSConfiguration			PRESENCE optional}|
	{ ID id-SFNInitialisationTime		CRITICALITY ignore	TYPE RelativeTime1900			PRESENCE optional}|
	{ ID id-UETxTEGAssociationList		CRITICALITY ignore	TYPE UETxTEGAssociationList		PRESENCE optional}|
	{ ID id-SRSTransmissionStatus		CRITICALITY ignore	TYPE SRSTransmissionStatus	PRESENCE optional}|
	{ ID id-NewCellIdentity				CRITICALITY ignore	TYPE CGI-NR						PRESENCE optional}|
	{ ID id-Remote-UE-Status			CRITICALITY ignore	TYPE Remote-UE-Status			PRESENCE optional},
		...
	}
	
-- **************************************************************
--
-- MEASUREMENT REQUEST
--
-- **************************************************************
	
	MeasurementRequest ::= SEQUENCE {
		protocolIEs		ProtocolIE-Container	{{MeasurementRequest-IEs}},
		...
	}
	
	MeasurementRequest-IEs NRPPA-PROTOCOL-IES ::= {
		{ ID id-LMF-Measurement-ID			CRITICALITY reject	TYPE Measurement-ID					PRESENCE mandatory}|
		{ ID id-TRP-MeasurementRequestList		CRITICALITY reject	TYPE TRP-MeasurementRequestList	PRESENCE mandatory}|
		{ ID id-ReportCharacteristics			CRITICALITY reject	TYPE ReportCharacteristics		PRESENCE mandatory}|
		{ ID id-MeasurementPeriodicity			CRITICALITY reject	TYPE MeasurementPeriodicity		PRESENCE conditional}|
	-- The IE shall be present if the Report Characteritics IE is set to the value “periodic” –
	{ ID id-TRPMeasurementQuantities		CRITICALITY reject	TYPE TRPMeasurementQuantities	PRESENCE mandatory}|
		{ ID id-SFNInitialisationTime			CRITICALITY ignore	TYPE RelativeTime1900			PRESENCE optional}|
		{ ID id-SRSConfiguration				CRITICALITY ignore	TYPE SRSConfiguration			PRESENCE optional}|
		{ ID id-MeasurementBeamInfoRequest		CRITICALITY ignore	TYPE MeasurementBeamInfoRequest	PRESENCE optional}|
		{ ID id-SystemFrameNumber				CRITICALITY ignore	TYPE SystemFrameNumber			PRESENCE optional}|
		{ ID id-SlotNumber						CRITICALITY ignore	TYPE SlotNumber					PRESENCE optional}|
		{ ID id-MeasurementPeriodicityExtended	CRITICALITY reject	TYPE MeasurementPeriodicityExtended PRESENCE conditional}|
	-- The IE shall be present the MeasurementPeriodicity IE is set to the value "extended"
	{ ID id-ResponseTime					CRITICALITY ignore	TYPE ResponseTime				PRESENCE optional}|
	{ ID id-MeasurementCharacteristicsRequestIndicator			CRITICALITY ignore	TYPE MeasurementCharacteristicsRequestIndicator	PRESENCE optional}|
	{ ID id-MeasurementTimeOccasion			CRITICALITY ignore	TYPE MeasurementTimeOccasion	PRESENCE optional}|
	{ ID id-MeasurementAmount				CRITICALITY ignore	TYPE MeasurementAmount			PRESENCE optional}|
	{ ID id-TimeWindowInformation-Measurement-List	CRITICALITY ignore	TYPE TimeWindowInformation-Measurement-List			PRESENCE optional	},
		...
	}
	
-- **************************************************************
--
-- MEASUREMENT RESPONSE
--
-- **************************************************************
	
	MeasurementResponse ::= SEQUENCE {
		protocolIEs		ProtocolIE-Container	{{MeasurementResponse-IEs}},
		...
	}
	
MeasurementResponse-IEs NRPPA-PROTOCOL-IES ::= {
	{ ID id-LMF-Measurement-ID		CRITICALITY reject	TYPE Measurement-ID				PRESENCE mandatory}|
	{ ID id-RAN-Measurement-ID		CRITICALITY reject	TYPE Measurement-ID				PRESENCE mandatory}|
	{ ID id-TRP-MeasurementResponseList	CRITICALITY reject	TYPE TRP-MeasurementResponseList PRESENCE optional}|
	{ ID id-CriticalityDiagnostics		CRITICALITY ignore	TYPE CriticalityDiagnostics		PRESENCE optional},
	...
	}

-- **************************************************************
--
-- MEASUREMENT FAILURE
--
-- **************************************************************
	
	MeasurementFailure ::= SEQUENCE {
		protocolIEs						ProtocolIE-Container		{{MeasurementFailure-IEs}},
		...
	}
	
	MeasurementFailure-IEs NRPPA-PROTOCOL-IES ::= {
		{ ID id-LMF-Measurement-ID		CRITICALITY reject	TYPE Measurement-ID				PRESENCE mandatory}|
		{ ID id-Cause						CRITICALITY ignore	TYPE Cause						PRESENCE mandatory}|
		{ ID id-CriticalityDiagnostics		CRITICALITY ignore	TYPE CriticalityDiagnostics		PRESENCE optional},
		...
	}
	
-- **************************************************************
--
-- MEASUREMENT REPORT
--
-- **************************************************************
	
	MeasurementReport ::= SEQUENCE {
		protocolIEs		ProtocolIE-Container	{{MeasurementReport-IEs}},
		...
	}
	
MeasurementReport-IEs NRPPA-PROTOCOL-IES ::= {
	{ ID id-LMF-Measurement-ID		CRITICALITY reject	TYPE Measurement-ID				PRESENCE mandatory}|
	{ ID id-RAN-Measurement-ID		CRITICALITY reject	TYPE Measurement-ID				PRESENCE mandatory}|
	{ ID id-TRP-MeasurementReportList			CRITICALITY reject	TYPE TRP-MeasurementResponseList PRESENCE mandatory},
	...
	}
	
-- **************************************************************
--
-- MEASUREMENT UPDATE
--
-- **************************************************************
	
	MeasurementUpdate ::= SEQUENCE {
		protocolIEs		ProtocolIE-Container	{{MeasurementUpdate-IEs}},
		...
	}
	
	MeasurementUpdate-IEs NRPPA-PROTOCOL-IES ::= {
		{ ID id-LMF-Measurement-ID			CRITICALITY reject	TYPE Measurement-ID				PRESENCE mandatory}|
		{ ID id-RAN-Measurement-ID			CRITICALITY reject	TYPE Measurement-ID				PRESENCE mandatory}| 
	{ ID id-SRSConfiguration			CRITICALITY ignore	TYPE SRSConfiguration			PRESENCE optional}|
	{ ID id-TRP-MeasurementUpdateList	CRITICALITY reject	TYPE TRP-MeasurementUpdateList	PRESENCE optional}|
		{ ID id-MeasurementCharacteristicsRequestIndicator	CRITICALITY ignore	TYPE	MeasurementCharacteristicsRequestIndicator	PRESENCE optional}|
		{ ID id-MeasurementTimeOccasion		CRITICALITY ignore	TYPE MeasurementTimeOccasion	PRESENCE optional},
		...
	}
	
-- **************************************************************
--
-- MEASUREMENT ABORT
--
-- **************************************************************
	
	MeasurementAbort ::= SEQUENCE {
		protocolIEs		ProtocolIE-Container	{{MeasurementAbort-IEs}},
		...
	}
	
	MeasurementAbort-IEs NRPPA-PROTOCOL-IES ::= {
		{ ID id-LMF-Measurement-ID		CRITICALITY reject	TYPE Measurement-ID				PRESENCE mandatory}|
		{ ID id-RAN-Measurement-ID		CRITICALITY reject	TYPE Measurement-ID				PRESENCE mandatory},
	
		...
	}
	
-- **************************************************************
--
-- MEASUREMENT FAILURE INDICATION
--
-- **************************************************************
	
	MeasurementFailureIndication ::= SEQUENCE {
		protocolIEs						ProtocolIE-Container		{{MeasurementFailureIndication-IEs}},
		...
	}
	
	MeasurementFailureIndication-IEs NRPPA-PROTOCOL-IES ::= {
		{ ID id-LMF-Measurement-ID		CRITICALITY reject	TYPE Measurement-ID				PRESENCE mandatory}|
		{ ID id-RAN-Measurement-ID		CRITICALITY reject	TYPE Measurement-ID				PRESENCE mandatory}|
		{ ID id-Cause					CRITICALITY ignore	TYPE Cause						PRESENCE mandatory},
		...
	}
	
-- **************************************************************
--
-- TRP INFORMATION REQUEST
--
-- **************************************************************
	
	TRPInformationRequest ::= SEQUENCE {
		protocolIEs		ProtocolIE-Container	{{TRPInformationRequest-IEs}},
		...
	}
	
	TRPInformationRequest-IEs NRPPA-PROTOCOL-IES ::= {
		{ ID id-TRPList							CRITICALITY ignore	TYPE TRPList				PRESENCE optional}|
		{ ID id-TRPInformationTypeListTRPReq	CRITICALITY reject	TYPE TRPInformationTypeListTRPReq	PRESENCE mandatory},
		...
	}
	
-- **************************************************************
--
-- TRP INFORMATION RESPONSE
--
-- **************************************************************
	
	TRPInformationResponse ::= SEQUENCE {
		protocolIEs		ProtocolIE-Container	{{TRPInformationResponse-IEs}},
		...
	}
	
	TRPInformationResponse-IEs NRPPA-PROTOCOL-IES ::= {
		{ ID id-TRPInformationListTRPResp				CRITICALITY ignore	TYPE TRPInformationListTRPResp			PRESENCE mandatory}|
		{ ID id-CriticalityDiagnostics			CRITICALITY ignore	TYPE CriticalityDiagnostics		PRESENCE optional},
		...
	}
	
-- **************************************************************
--
-- TRP INFORMATION FAILURE
--
-- **************************************************************
	
	TRPInformationFailure ::= SEQUENCE {
		protocolIEs						ProtocolIE-Container		{{TRPInformationFailure-IEs}},
		...
	}
	
	TRPInformationFailure-IEs NRPPA-PROTOCOL-IES ::= {
		{ ID id-Cause						CRITICALITY ignore	TYPE Cause						PRESENCE mandatory}|
		{ ID id-CriticalityDiagnostics		CRITICALITY ignore	TYPE CriticalityDiagnostics		PRESENCE optional},
		...
	}
	
	

-- **************************************************************
--
-- POSITIONING ACTIVATION REQUEST
--
-- **************************************************************

PositioningActivationRequest ::= SEQUENCE {
	protocolIEs			ProtocolIE-Container       { { PositioningActivationRequestIEs} },
	...
}

PositioningActivationRequestIEs NRPPA-PROTOCOL-IES ::= {
	{ ID id-SRSType					CRITICALITY reject	TYPE SRSType					PRESENCE mandatory	} |
	{ ID id-ActivationTime			CRITICALITY ignore	TYPE RelativeTime1900				PRESENCE optional	},
	...
} 

SRSType ::= CHOICE {
	semipersistentSRS				SemipersistentSRS,
	aperiodicSRS					AperiodicSRS, 
	choice-Extension				ProtocolIE-Single-Container { { SRSType-ExtIEs} }
}

SRSType-ExtIEs NRPPA-PROTOCOL-IES ::= {
	...
}

SemipersistentSRS ::= SEQUENCE {
	sRSResourceSetID			SRSResourceSetID,
	iE-Extensions				ProtocolExtensionContainer { {SemipersistentSRS-ExtIEs} } OPTIONAL,
	...
}

SemipersistentSRS-ExtIEs NRPPA-PROTOCOL-EXTENSION ::= {		
	{ ID id-SRSSpatialRelation						CRITICALITY ignore	EXTENSION SpatialRelationInfo					PRESENCE optional}|
	{ ID id-SRSSpatialRelationPerSRSResource		CRITICALITY ignore	EXTENSION SpatialRelationPerSRSResource		PRESENCE optional}|
	{ ID id-PosSRSResourceSet-Aggregation-List		CRITICALITY ignore	EXTENSION PosSRSResourceSet-Aggregation-List		PRESENCE optional},
	...
}

AperiodicSRS ::= SEQUENCE {
	aperiodic					ENUMERATED{true,...},
	sRSResourceTrigger			SRSResourceTrigger OPTIONAL, 
	iE-Extensions				ProtocolExtensionContainer { {AperiodicSRS-ExtIEs} } OPTIONAL,
	...
}

AperiodicSRS-ExtIEs NRPPA-PROTOCOL-EXTENSION ::= {
	{ ID id-PosSRSResourceSet-Aggregation-List		CRITICALITY ignore	EXTENSION PosSRSResourceSet-Aggregation-List		PRESENCE optional},
	...
}


-- **************************************************************
--
-- POSITIONING ACTIVATION RESPONSE
--
-- **************************************************************

PositioningActivationResponse ::= SEQUENCE {
	protocolIEs			ProtocolIE-Container       { { PositioningActivationResponseIEs} },
	...
}


PositioningActivationResponseIEs NRPPA-PROTOCOL-IES ::= {
	{ ID id-CriticalityDiagnostics		CRITICALITY ignore	TYPE CriticalityDiagnostics		PRESENCE optional }|
	{ ID id-SystemFrameNumber			CRITICALITY ignore	TYPE SystemFrameNumber			PRESENCE optional }|
	{ ID id-SlotNumber					CRITICALITY ignore	TYPE SlotNumber					PRESENCE optional },
	...
}



-- **************************************************************
--
-- POSITIONING ACTIVATION FAILURE
--
-- **************************************************************

PositioningActivationFailure ::= SEQUENCE {
	protocolIEs			ProtocolIE-Container       { { PositioningActivationFailureIEs} },
	...
}

PositioningActivationFailureIEs NRPPA-PROTOCOL-IES ::= {
	{ ID id-Cause						CRITICALITY ignore	TYPE Cause						PRESENCE mandatory	}|
	{ ID id-CriticalityDiagnostics		CRITICALITY ignore	TYPE CriticalityDiagnostics		PRESENCE optional },
	...
}


-- **************************************************************
--
-- POSITIONING DEACTIVATION
--
-- **************************************************************

PositioningDeactivation ::= SEQUENCE {
	protocolIEs			ProtocolIE-Container       { { PositioningDeactivationIEs} },
	...
}

PositioningDeactivationIEs NRPPA-PROTOCOL-IES ::= {
	{ ID id-AbortTransmission			CRITICALITY ignore	TYPE AbortTransmission		PRESENCE mandatory	} ,
	...
} 

-- **************************************************************
--
-- PRS CONFIGURATION REQUEST
--
-- **************************************************************

PRSConfigurationRequest ::= SEQUENCE {
	protocolIEs		ProtocolIE-Container	{{PRSConfigurationRequest-IEs}},
	...
}

PRSConfigurationRequest-IEs NRPPA-PROTOCOL-IES ::= {
	{ ID id-PRSConfigRequestType	CRITICALITY reject	TYPE PRSConfigRequestType				PRESENCE mandatory}|
	{ ID id-PRSTRPList				CRITICALITY ignore	TYPE PRSTRPList							PRESENCE mandatory},
	...
}

-- **************************************************************
--
-- PRS CONFIGURATION RESPONSE
--
-- **************************************************************

PRSConfigurationResponse ::= SEQUENCE {
	protocolIEs		ProtocolIE-Container	{{ PRSConfigurationResponse-IEs}},
	...
}

PRSConfigurationResponse-IEs NRPPA-PROTOCOL-IES ::= {
	{ ID id-PRSTransmissionTRPList	CRITICALITY ignore	TYPE PRSTransmissionTRPList			PRESENCE optional}|
	{ ID id-CriticalityDiagnostics	CRITICALITY ignore	TYPE CriticalityDiagnostics			PRESENCE optional},
	...
}

-- **************************************************************
--
-- PRS CONFIGURATION FAILURE
--
-- **************************************************************

PRSConfigurationFailure ::= SEQUENCE {
	protocolIEs		ProtocolIE-Container	{{ PRSConfigurationFailure-IEs}},
	...
}

PRSConfigurationFailure-IEs NRPPA-PROTOCOL-IES ::= {
	{ ID id-Cause					CRITICALITY ignore	TYPE Cause						PRESENCE mandatory}|
	{ ID id-CriticalityDiagnostics	CRITICALITY ignore	TYPE CriticalityDiagnostics		PRESENCE optional},
	...
}


-- **************************************************************
--
-- MEASUREMENT PRECONFIGURATION REQUIRED
--
-- **************************************************************

MeasurementPreconfigurationRequired ::= SEQUENCE {
	protocolIEs		ProtocolIE-Container	{{ MeasurementPreconfigurationRequired-IEs}},
	...
}

MeasurementPreconfigurationRequired-IEs NRPPA-PROTOCOL-IES ::= {
	{ ID id-TRP-PRS-Information-List	CRITICALITY ignore	TYPE TRP-PRS-Information-List	PRESENCE mandatory},
	...
}

-- **************************************************************
--
-- MEASUREMENT PRECONFIGURATION CONFIRM
--
-- **************************************************************

MeasurementPreconfigurationConfirm::= SEQUENCE {
	protocolIEs		ProtocolIE-Container	{{ MeasurementPreconfigurationConfirm-IEs}},
	...
}

MeasurementPreconfigurationConfirm-IEs NRPPA-PROTOCOL-IES ::= {
	{ ID id-PreconfigurationResult		CRITICALITY	ignore	TYPE PreconfigurationResult		PRESENCE mandatory }|
	{ ID id-CriticalityDiagnostics		CRITICALITY ignore	TYPE CriticalityDiagnostics		PRESENCE optional },
	...
}

-- **************************************************************
--
-- MEASUREMENT PRECONFIGURATION REFUSE
--
-- **************************************************************

MeasurementPreconfigurationRefuse::= SEQUENCE {
	protocolIEs		ProtocolIE-Container	{{ MeasurementPreconfigurationRefuse-IEs}},
	...
}

MeasurementPreconfigurationRefuse-IEs NRPPA-PROTOCOL-IES ::= {
	{ ID id-Cause					CRITICALITY ignore	TYPE Cause						PRESENCE mandatory}|
	{ ID id-CriticalityDiagnostics	CRITICALITY ignore	TYPE CriticalityDiagnostics		PRESENCE optional},
	...
}

-- **************************************************************
--
-- MEASUREMENT ACTIVATION 
--
-- **************************************************************

MeasurementActivation::= SEQUENCE {
	protocolIEs			ProtocolIE-Container       { { MeasurementActivation-IEs} },
	...
}

MeasurementActivation-IEs NRPPA-PROTOCOL-IES ::= {
	{ ID id-RequestType					CRITICALITY reject	TYPE RequestType 					PRESENCE mandatory}|
	{ ID id-PRS-Measurements-Info-List	CRITICALITY ignore	TYPE PRS-Measurements-Info-List		PRESENCE optional},
	...
}
	
-- **************************************************************
--
-- SRS INFORMATION RESERVATION NOTIFICATION
--
-- **************************************************************

SRSInformationReservationNotification	::= SEQUENCE {
	protocolIEs		ProtocolIE-Container	{{ SRSInformationReservationNotification-IEs}},
	...
}

SRSInformationReservationNotification-IEs NRPPA-PROTOCOL-IES ::= {
	{ ID id-SRSReservationType	CRITICALITY reject	TYPE SRSReservationType								PRESENCE mandatory}|
	{ ID id-SRSInformation		CRITICALITY ignore	TYPE RequestedSRSTransmissionCharacteristics		PRESENCE optional}|
	{ ID id-PreconfiguredSRSInformation	CRITICALITY ignore	TYPE RequestedSRSPreconfigurationCharacteristics-List		PRESENCE optional},
	...
}

-- **************************************************************
--
-- POSITIONING DATA COLLECTION REPORT
--
-- **************************************************************

PositioningDataCollectionReport ::= SEQUENCE {
	protocolIEs		ProtocolIE-Container	{{ PositioningDataCollectionReport-IEs}},
	...
}

PositioningDataCollectionReport-IEs NRPPA-PROTOCOL-IES ::= {
		{ ID id-LMF-Measurement-ID			CRITICALITY reject	TYPE Measurement-ID		PRESENCE mandatory}|
		{ ID id-RAN-Measurement-ID			CRITICALITY reject	TYPE Measurement-ID		PRESENCE mandatory}|
		{ ID id-PositioningDataInformation	CRITICALITY ignore	TYPE PositioningDataInformation	PRESENCE optional}|
	{ ID id-PositioningDataUnavailable	CRITICALITY ignore	TYPE PositioningDataUnavailable	PRESENCE optional},
	...
}
	
	
	END

-- **************************************************************
--
-- Information Element Definitions
--
-- **************************************************************
	
	NRPPA-IEs {
	itu-t (0) identified-organization (4) etsi (0) mobileDomain (0) 
	ngran-access (22) modules (3) nrppa (4) version1 (1) nrppa-IEs (2) }
	
	DEFINITIONS AUTOMATIC TAGS ::= 
	
	BEGIN
	
IMPORTS	
	
	id-MeasurementQuantities-Item,
	id-CGI-NR,
	id-SFNInitialisationTime-NR,
	id-GeographicalCoordinates,
	id-ResultSS-RSRP,
	id-ResultSS-RSRQ,
	id-ResultCSI-RSRP,
	id-ResultCSI-RSRQ,
	id-AngleOfArrivalNR,
	id-ResultNR,
	id-ResultEUTRA,
	maxCellinRANnode,
	maxCellReport,
	maxNrOfErrors,
	maxNoMeas,
	maxnoOTDOAtypes,
	maxServCell,
	id-OtherRATMeasurementQuantities-Item,
	id-WLANMeasurementQuantities-Item,
	maxGERANMeas,
	maxUTRANMeas,
	maxWLANchannels,
	maxnoFreqHoppingBandsMinusOne,
	id-TDD-Config-EUTRA-Item,
	maxNrOfPosSImessage,
	maxnoAssistInfoFailureListItems,
	maxNrOfSegments,
	maxNrOfPosSIBs,
	maxnoPosMeas,
	maxnoTRPs,
	maxnoTRPInfoTypes,
	maxNoOfMeasTRPs,
	maxNoPath,
	maxnoofAngleInfo,
	maxnolcs-gcs-translation,
	maxnoBcastCell,
	maxnoSRSTriggerStates,
	maxnoSpatialRelations,
	maxNRMeas,
	maxEUTRAMeas,
	maxIndexesReport,
	maxCellReportNR,
	maxnoSRS-Carriers,
	maxnoSCSs,
	maxnoSRS-Resources,
	maxnoSRS-PosResources,
	maxnoSRS-ResourceSets,
	maxnoSRS-ResourcePerSet,
	maxnoSRS-PosResourceSets,
	maxnoSRS-PosResourcePerSet,
	maxPRS-ResourceSets,
	maxPRS-ResourcesPerSet,
	maxNoSSBs,
	maxnoofPRSresourceSet,
	maxnoofPRSresource,
	maxnoofULAoAs,
	maxNoPathExtended,
	maxnoARPs,
	maxnoTRPTEGs,
	maxnoUETEGs,
	maxFreqLayers,
	maxnoPRSTRPs,
	maxNumResourcesPerAngle,
	maxnoAzimuthAngles,
	maxnoElevationAngles,
	maxnoVACell,
	maxnoaggregatedPosSRS-Resources,
	maxnoaggregatedPosSRS-ResourceSets,
	maxnoAggPosPRSResourceSets,
	maxnoofTimeWindowSRS,
	maxnoofTimeWindowMeas,
	maxnoPreconfiguredSRS,
	maxnoofHopsMinusOne,
	maxnoAggCombinations,
	maxnoAggregatedPosSRSCombinations,
	maxnoofChannelRes,
	id-Cell-ID,
	id-TRPInformationTypeItem,
	id-SrsFrequency,
	id-TRPType,
	id-SRSSpatialRelationPerSRSResource,
	id-PRS-Resource-ID,
	id-OnDemandPRS,
	id-AoA-SearchWindow,
	id-ZoA,
	id-MultipleULAoA,
	id-UL-SRS-RSRPP,
	id-SRSResourcetype,
	id-ExtendedAdditionalPathList,
	id-ARPLocationInfo,
	id-ARP-ID,
	id-LoS-NLoSInformation,
	id-NumberOfTRPRxTEG,
	id-NumberOfTRPRxTxTEG,
	id-TRPTxTEGAssociation,
	id-TRPTEGInformation,
	id-TRP-Rx-TEGInformation,
	id-TRPBeamAntennaInformation,
	id-NR-TADV,
	id-pathPower,
	id-SRSPortIndex,
	id-UETxTimingErrorMargin,
	id-nrofSymbolsExtended,
	id-repetitionFactorExtended,
	id-StartRBHopping,
	id-StartRBIndex,
	id-transmissionCombn8,
	id-ExtendedResourceSymbolOffset,
	id-Mobile-TRP-LocationInformation,
	id-Mobile-IAB-MT-UE-ID,
	id-MobileAccessPointLocation,
	id-CommonTAParameters,
	id-UE-Rx-Tx-Time-Diff,
	id-SCS-480,
	id-SCS-960,
	id-UL-RSCPMeas,
	id-Bandwidth-Aggregation-Request-Indication,
	id-PosSRSResourceSet-Aggregation-List,
	id-ReportingGranularitykminus1,
	id-ReportingGranularitykminus2,
	id-ReportingGranularitykminus3,
	id-ReportingGranularitykminus4,
	id-ReportingGranularitykminus5,
	id-ReportingGranularitykminus6,
	id-SymbolIndex,
	id-TimingReportingGranularityFactorExtended,
	id-PosValidityAreaCellList,
	id-PRSBWAggregationRequestInfoList,
	id-AggregatedPosSRSResourceID-List,
	id-AggregatedPRSResourceSetList,
	id-TRPPhaseQuality,
	id-ValidityAreaSpecificSRSInformation,
	id-TxHoppingConfiguration,
	id-MeasuredFrequencyHops,
	id-ReportingGranularitykminus1AdditionalPath,
	id-ReportingGranularitykminus2AdditionalPath,
	id-ReportingGranularitykminus3AdditionalPath,
	id-ReportingGranularitykminus4AdditionalPath,
	id-ReportingGranularitykminus5AdditionalPath,
	id-ReportingGranularitykminus6AdditionalPath,
	id-MeasuredResultsAssociatedInfoList,
	id-PointA,
	id-NR-PCI,
	id-SCS-SpecificCarrier,
	id-MeasBasedOnAggregatedResources,
	id-UEReportingInterval-milliseconds,
	id-LocalOrigin,
	id-DL-reference-signal-UERxTx-TD,
	id-SRSPosPeriodicConfigHyperSFNIndex,
	id-ValidityAreaSpecificSRSInformationExtended,
	id-E-CID-AoA-NR-per-TRP,
	id-WAB-MT-UE-ID,
	id-ChannelResponseInformation,
	id-UL-SRS-TDCT,
	id-Inferred-measurement,
	id-PositioningDataCollectionNeeded





FROM NRPPA-Constants

	Criticality,
	NRPPATransactionID,
	ProcedureCode,
	ProtocolIE-ID,
	TriggeringMessage

FROM NRPPA-CommonDataTypes

	ProtocolExtensionContainer{},
	ProtocolIE-Single-Container{},
	
	NRPPA-PROTOCOL-EXTENSION,
	NRPPA-PROTOCOL-IES

FROM NRPPA-Containers;

-- A

AbortTransmission ::= CHOICE {
	deactivateSRSResourceSetID		SRSResourceSetID,
	releaseALL						NULL,
	choice-extension							ProtocolIE-Single-Container { { AbortTransmission-ExtIEs } }
}

AbortTransmission-ExtIEs NRPPA-PROTOCOL-IES ::= {
	{ ID id-PosSRSResourceSet-Aggregation-List	CRITICALITY ignore TYPE PosSRSResourceSet-Aggregation-List		PRESENCE mandatory },
	...
}

ActiveULBWP  ::= SEQUENCE {
	locationAndBandwidth		INTEGER (0..37949,...),
	subcarrierSpacing           ENUMERATED {kHz15, kHz30, kHz60, kHz120,..., kHz480, kHz960},
	cyclicPrefix				ENUMERATED {normal, extended},
	txDirectCurrentLocation		INTEGER (0..3301,...),
	shift7dot5kHz				ENUMERATED {true, ...} OPTIONAL,
	sRSConfig					SRSConfig,
	iE-Extensions				ProtocolExtensionContainer { { ActiveULBWP-ExtIEs} } OPTIONAL,
	...
}

ActiveULBWP-ExtIEs NRPPA-PROTOCOL-EXTENSION ::= {
	...
}


AdditionalPathList ::= SEQUENCE (SIZE (1.. maxNoPath)) OF AdditionalPathListItem


AdditionalPathListItem ::= SEQUENCE {
	relativeTimeOfPath	RelativePathDelay,
	pathQuality			TrpMeasurementQuality	OPTIONAL,  
	iE-Extensions		ProtocolExtensionContainer { { AdditionalPathListItem-ExtIEs} } OPTIONAL,
	...
}

AdditionalPathListItem-ExtIEs NRPPA-PROTOCOL-EXTENSION ::= {
	{ ID id-MultipleULAoA	CRITICALITY ignore EXTENSION MultipleULAoA PRESENCE	optional}|
	{ ID id-pathPower		CRITICALITY ignore EXTENSION UL-SRS-RSRPP PRESENCE	optional},
	...
}

AggregatedPosSRSResourceID-List ::= SEQUENCE (SIZE (2..maxnoaggregatedPosSRS-Resources)) OF AggregatedPosSRSResourceID-Item

AggregatedPosSRSResourceID-Item ::= SEQUENCE {
	sRSPosResource-ID	SRSPosResourceID,  
	iE-Extensions		ProtocolExtensionContainer { { AggregatedPosSRSResourceID-Item-ExtIEs} } OPTIONAL,
	...
}

AggregatedPosSRSResourceID-Item-ExtIEs NRPPA-PROTOCOL-EXTENSION ::= {
		{ ID id-PointA					CRITICALITY ignore EXTENSION PointA 				PRESENCE	mandatory}|
				{ ID id-SCS-SpecificCarrier	CRITICALITY ignore EXTENSION SCS-SpecificCarrier 	PRESENCE	mandatory}|
	{ ID id-NR-PCI						CRITICALITY ignore EXTENSION NR-PCI 				PRESENCE	optional},
	...
}


AggregatedPRSResourceSetList ::= SEQUENCE (SIZE (1..maxnoAggCombinations)) OF AggregatedPRSResourceSet-Item

AggregatedPRSResourceSet-Item ::= SEQUENCE {
	dl-PRS-ResourceSet-List			DL-PRS-ResourceSet-List,
	iE-Extensions					ProtocolExtensionContainer { { AggregatedPRSResourceSet-Item-ExtIEs} } OPTIONAL,
	...
}

AggregatedPRSResourceSet-Item-ExtIEs NRPPA-PROTOCOL-EXTENSION ::= {
	...
}

DL-PRS-ResourceSet-List ::= SEQUENCE (SIZE (1..maxnoAggPosPRSResourceSets)) OF DL-PRS-ResourceSet-Item

DL-PRS-ResourceSet-Item ::= SEQUENCE {
	dl-prs-ResourceSetIndex				INTEGER (1..8),
	iE-Extensions						ProtocolExtensionContainer { { DL-PRS-ResourceSet-Item-ExtIEs} } OPTIONAL,
	...
}

DL-PRS-ResourceSet-Item-ExtIEs NRPPA-PROTOCOL-EXTENSION ::= {
	...
}


ExtendedAdditionalPathList ::= SEQUENCE (SIZE (1.. maxNoPathExtended)) OF ExtendedAdditionalPathList-Item


ExtendedAdditionalPathList-Item ::= SEQUENCE {
	relativeTimeOfPath	RelativePathDelay,
	pathQuality			TrpMeasurementQuality	OPTIONAL,
	multipleULAoA		MultipleULAoA  			OPTIONAL,
	pathPower			UL-SRS-RSRPP			OPTIONAL,
	iE-Extensions		ProtocolExtensionContainer { { ExtendedAdditionalPathList-Item-ExtIEs} } OPTIONAL,
	...
}

ExtendedAdditionalPathList-Item-ExtIEs NRPPA-PROTOCOL-EXTENSION ::= {
	...
}

AoA-AssistanceInfo ::= SEQUENCE {
	angleMeasurement	AngleMeasurementType,
	lCS-to-GCS-Translation	LCS-to-GCS-Translation		OPTIONAL,
	iE-Extensions				ProtocolExtensionContainer { { AoA-AssistanceInfo-ExtIEs } } OPTIONAL,
	...
}

AoA-AssistanceInfo-ExtIEs NRPPA-PROTOCOL-EXTENSION ::= {
	...
}

AperiodicSRSResourceTriggerList ::= SEQUENCE (SIZE(1..maxnoSRSTriggerStates)) OF AperiodicSRSResourceTrigger

AperiodicSRSResourceTrigger ::= INTEGER (1..3)

AngleMeasurementType ::= CHOICE {	
	expected-ULAoA		Expected-UL-AoA,
	expected-ZoA		Expected-ZoA-only,
	choice-extension ProtocolIE-Single-Container { { AngleMeasurementType-ExtIEs } }
}

AngleMeasurementType-ExtIEs NRPPA-PROTOCOL-IES ::= {
...
}

Expected-UL-AoA ::= SEQUENCE {
	expected-Azimuth-AoA		Expected-Azimuth-AoA,
	expected-Zenith-AoA		Expected-Zenith-AoA		OPTIONAL,
	iE-extensions		ProtocolExtensionContainer { { Expected-UL-AoA-ExtIEs } }	OPTIONAL,
	...
}

Expected-UL-AoA-ExtIEs NRPPA-PROTOCOL-EXTENSION ::= {
	...
}

Expected-ZoA-only ::= SEQUENCE {
	expected-ZoA-only	Expected-Zenith-AoA,
	iE-extensions		ProtocolExtensionContainer { { Expected-ZoA-only-ExtIEs } }	OPTIONAL,
	...
}

Expected-ZoA-only-ExtIEs NRPPA-PROTOCOL-EXTENSION ::= {
	...
}

Expected-Azimuth-AoA ::= SEQUENCE {
	expected-Azimuth-AoA-value			Expected-Value-AoA,
	expected-Azimuth-AoA-uncertainty		Uncertainty-range-AoA,
	iE-extensions		ProtocolExtensionContainer { { Expected-Azimuth-AoA-ExtIEs } }	OPTIONAL,
	...
}

Expected-Azimuth-AoA-ExtIEs NRPPA-PROTOCOL-EXTENSION ::= {
	...
}

Expected-Zenith-AoA ::= SEQUENCE {
	expected-Zenith-AoA-value			Expected-Value-ZoA,
	expected-Zenith-AoA-uncertainty		Uncertainty-range-ZoA,
	iE-extensions		ProtocolExtensionContainer { { Expected-Zenith-AoA-ExtIEs } }	OPTIONAL,
	...
}

Expected-Zenith-AoA-ExtIEs NRPPA-PROTOCOL-EXTENSION ::= {
	...
}

ARP-ID ::= INTEGER (1..16, ...)

ARPLocationInformation ::= SEQUENCE (SIZE (1..maxnoARPs)) OF ARPLocationInformation-Item

ARPLocationInformation-Item ::= SEQUENCE {
	aRP-ID				ARP-ID,
	aRPLocationType		ARPLocationType,
	iE-Extensions		ProtocolExtensionContainer { { ARPLocationInformation-ExtIEs} } OPTIONAL,
	...
}

ARPLocationInformation-ExtIEs NRPPA-PROTOCOL-EXTENSION ::= {
	...
}

ARPLocationType ::= CHOICE {
	aRPPositionRelativeGeodetic			RelativeGeodeticLocation,
	aRPPositionRelativeCartesian		RelativeCartesianLocation,
	choice-extension					ProtocolIE-Single-Container { { ARPLocationType-ExtIEs } }
}

ARPLocationType-ExtIEs NRPPA-PROTOCOL-IES ::= {
	...
}

Assistance-Information ::= SEQUENCE {
	systemInformation				SystemInformation,
	iE-Extensions					ProtocolExtensionContainer { { Assistance-Information-ExtIEs} } OPTIONAL,
	...
}

Assistance-Information-ExtIEs NRPPA-PROTOCOL-EXTENSION ::= {
	...
}

AssistanceInformationFailureList ::= SEQUENCE (SIZE (1..maxnoAssistInfoFailureListItems)) OF SEQUENCE {
	posSIB-Type						PosSIB-Type,
	outcome							Outcome,
	iE-Extensions					ProtocolExtensionContainer { {AssistanceInformationFailureList-ExtIEs} }	OPTIONAL,
	...
}

AssistanceInformationFailureList-ExtIEs NRPPA-PROTOCOL-EXTENSION ::= {
	...
}

AssistanceInformationMetaData ::= SEQUENCE {
	encrypted			ENUMERATED {true, ...}	OPTIONAL,
	gNSSID				ENUMERATED {gps, sbas, qzss, galileo, glonass, bds, navic, ...}	OPTIONAL,
	sBASID				ENUMERATED {waas, egnos, msas, gagan, ...}					OPTIONAL,
	iE-Extensions		ProtocolExtensionContainer { { AssistanceInformationMetaData-ExtIEs} }	OPTIONAL,
	...
}

AssistanceInformationMetaData-ExtIEs NRPPA-PROTOCOL-EXTENSION ::= {
	...
}



-- B

BandwidthSRS ::= CHOICE {
	fR1		ENUMERATED {mHz5, mHz10, mHz20, mHz40, mHz50, mHz80, mHz100, ... ,mHz160, mHz200, mHz15, mHz25, mHz30, mHz60, mHz35, mHz45, mHz70, mHz90},
	fR2		ENUMERATED {mHz50, mHz100, mHz200, mHz400, ..., mHz600, mhz800, mHz1600, mHz2000 },
	choice-extension		ProtocolIE-Single-Container { { BandwidthSRS-ExtIEs } }
}

BandwidthSRS-ExtIEs NRPPA-PROTOCOL-IES ::= {
	...
}

Bandwidth-Aggregation-Request-Indication ::= ENUMERATED { true, ...} 

BCCH ::= INTEGER (0..1023, ...)

Broadcast ::= ENUMERATED {
	start,
	stop,
	...
}

BroadcastPeriodicity ::= ENUMERATED {
	ms80,
	ms160,
	ms320,
	ms640,
	ms1280,
	ms2560,
	ms5120,
	...
}

PositioningBroadcastCells ::= SEQUENCE (SIZE (1..maxnoBcastCell)) OF NG-RAN-CGI 

BSSID ::= OCTET STRING (SIZE(6))

-- C

CarrierFreq ::= SEQUENCE {
	pointA				INTEGER (0..3279165),
	offsetToCarrier		INTEGER (0..2199, ...),
	iE-Extensions		ProtocolExtensionContainer { {CarrierFreq-ExtIEs} } OPTIONAL,
	...
}

CarrierFreq-ExtIEs NRPPA-PROTOCOL-EXTENSION ::= {
	...
}

Cause ::= CHOICE {
	radioNetwork		CauseRadioNetwork,
	protocol			CauseProtocol,
	misc				CauseMisc,
	choice-Extension	ProtocolIE-Single-Container {{ Cause-ExtensionIE }}
}

Cause-ExtensionIE NRPPA-PROTOCOL-IES ::= {
	...
}

CauseMisc ::= ENUMERATED {
	unspecified,
	...
}

CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}

CauseRadioNetwork ::= ENUMERATED {
	unspecified,
	requested-item-not-supported,
	requested-item-temporarily-not-available,
	...,
	serving-NG-RAN-node-changed,
	requested-item-not-supported-on-time

}

Cell-Portion-ID ::= INTEGER (0..4095,...)

CGI-EUTRA ::= SEQUENCE {
	pLMN-Identity				PLMN-Identity,
	eUTRAcellIdentifier			EUTRACellIdentifier,
	iE-Extensions				ProtocolExtensionContainer { {CGI-EUTRA-ExtIEs} } OPTIONAL,
	...
}

CGI-EUTRA-ExtIEs NRPPA-PROTOCOL-EXTENSION ::= {
	...
}


CGI-NR ::= SEQUENCE {
	pLMN-Identity				PLMN-Identity,
	nRcellIdentifier			NRCellIdentifier,
	iE-Extensions				ProtocolExtensionContainer { {CGI-NR-ExtIEs} } OPTIONAL,
	...
}

CGI-NR-ExtIEs NRPPA-PROTOCOL-EXTENSION ::= {
	...
}

ChannelResponseInformation ::= SEQUENCE {
	channelResponseWindowSize	ChannelResponseWindowSize,
	channelResponseNumber		ChannelResponseNumber,
	iE-Extensions				ProtocolExtensionContainer { { ChannelResponseInformation-ExtIEs} } OPTIONAL,
	...
}

ChannelResponseInformation-ExtIEs NRPPA-PROTOCOL-EXTENSION ::= {
	...
}

ChannelResponseWindowSize ::= ENUMERATED {ws32, ws64, ws128, ...}

ChannelResponseNumber ::= ENUMERATED {n8, n16, n24, ...}


CPLength-EUTRA ::= ENUMERATED {
	normal,
	extended,
	...
}

CriticalityDiagnostics ::= SEQUENCE {
	procedureCode					ProcedureCode					OPTIONAL,
	triggeringMessage				TriggeringMessage				OPTIONAL,
	procedureCriticality			Criticality					OPTIONAL,
	nrppatransactionID				NRPPATransactionID				OPTIONAL,
	iEsCriticalityDiagnostics		CriticalityDiagnostics-IE-List	OPTIONAL,
	iE-Extensions					ProtocolExtensionContainer { {CriticalityDiagnostics-ExtIEs} }	OPTIONAL,
	...
}


CriticalityDiagnostics-ExtIEs NRPPA-PROTOCOL-EXTENSION ::= {
	...
}

CriticalityDiagnostics-IE-List ::= SEQUENCE (SIZE (1..maxNrOfErrors)) OF
	SEQUENCE {
		iECriticality			Criticality,
		iE-ID					ProtocolIE-ID,
		typeOfError				TypeOfError,
		iE-Extensions			ProtocolExtensionContainer { {CriticalityDiagnostics-IE-List-ExtIEs} } OPTIONAL,
		...
}

CriticalityDiagnostics-IE-List-ExtIEs NRPPA-PROTOCOL-EXTENSION ::= {
	...
}

CommonTAParameters ::= SEQUENCE {
	epochTime				OCTET STRING,
	taInfo					OCTET STRING,
	iE-Extensions			ProtocolExtensionContainer {{ CommonTAParameters-ExtIEs}}				OPTIONAL,
	...
}

CommonTAParameters-ExtIEs NRPPA-PROTOCOL-EXTENSION ::= {
	...
}


-- D

DL-Bandwidth-EUTRA ::= ENUMERATED {
	bw6,
	bw15,
	bw25,
	bw50,
	bw75,
	bw100,
	...
}

DL-PRS ::= SEQUENCE {
	prsid 					PRS-ID,
	dl-PRSResourceSetID		PRS-Resource-Set-ID,
	dl-PRSResourceID		PRS-Resource-ID		OPTIONAL,
	iE-Extensions			ProtocolExtensionContainer { {DL-PRS-ExtIEs} }	OPTIONAL,
	...
}

DL-PRS-ExtIEs NRPPA-PROTOCOL-EXTENSION ::= {
	...
}

DL-PRSMutingPattern ::= CHOICE {
	two					BIT STRING (SIZE(2)),
	four				BIT STRING (SIZE(4)),
	six					BIT STRING (SIZE(6)),
	eight				BIT STRING (SIZE(8)),
	sixteen				BIT STRING (SIZE(16)),
	thirty-two			BIT STRING (SIZE(32)),
	choice-extension							ProtocolIE-Single-Container { { DL-PRSMutingPattern-ExtIEs } }
}

DL-PRSMutingPattern-ExtIEs NRPPA-PROTOCOL-IES ::= {
	...
}

DLPRSResourceCoordinates ::= SEQUENCE {
	listofDL-PRSResourceSetARP		SEQUENCE (SIZE(1.. maxPRS-ResourceSets)) OF DLPRSResourceSetARP,
	iE-Extensions					ProtocolExtensionContainer { { DLPRSResourceCoordinates-ExtIEs } } OPTIONAL,
	...
}

DLPRSResourceCoordinates-ExtIEs NRPPA-PROTOCOL-EXTENSION ::= {
	...
}

DLPRSResourceSetARP ::= SEQUENCE {
	dl-PRSResourceSetID				PRS-Resource-Set-ID,
	dL-PRSResourceSetARPLocation	DL-PRSResourceSetARPLocation,
	listofDL-PRSResourceARP			SEQUENCE (SIZE(1.. maxPRS-ResourcesPerSet)) OF DLPRSResourceARP,
	iE-Extensions					ProtocolExtensionContainer { { DLPRSResourceSetARP-ExtIEs } } OPTIONAL,
	...
}

DLPRSResourceSetARP-ExtIEs NRPPA-PROTOCOL-EXTENSION ::= {
	...
}


DL-PRSResourceSetARPLocation ::= CHOICE {
	relativeGeodeticLocation			RelativeGeodeticLocation,
	relativeCartesianLocation			RelativeCartesianLocation,
	choice-Extension					ProtocolIE-Single-Container { { DL-PRSResourceSetARPLocation-ExtIEs } }
}

DL-PRSResourceSetARPLocation-ExtIEs NRPPA-PROTOCOL-IES ::= {
	...
}


DLPRSResourceARP ::= SEQUENCE {
	dl-PRSResourceID			PRS-Resource-ID,
	dL-PRSResourceARPLocation	DL-PRSResourceARPLocation,	
	iE-Extensions				ProtocolExtensionContainer { { DLPRSResourceARP-ExtIEs } } OPTIONAL,
	...
}

DLPRSResourceARP-ExtIEs NRPPA-PROTOCOL-EXTENSION ::= {
	...
}

DL-PRSResourceARPLocation ::= CHOICE {
	relativeGeodeticLocation			RelativeGeodeticLocation,
	relativeCartesianLocation			RelativeCartesianLocation,
	choice-Extension					ProtocolIE-Single-Container { { DL-PRSResourceARPLocation-ExtIEs } }
}

DL-PRSResourceARPLocation-ExtIEs NRPPA-PROTOCOL-IES ::= {
	...
}

DL-reference-signal-UERxTx-TD ::= ENUMERATED {csirs, prs, ...}

-- E

E-CID-MeasurementResult ::= SEQUENCE {
	servingCell-ID					NG-RAN-CGI,
	servingCellTAC					TAC,
	nG-RANAccessPointPosition		NG-RANAccessPointPosition	OPTIONAL,
	measuredResults					MeasuredResults				OPTIONAL,
	iE-Extensions					ProtocolExtensionContainer { { E-CID-MeasurementResult-ExtIEs} } OPTIONAL,
	...
}

E-CID-MeasurementResult-ExtIEs NRPPA-PROTOCOL-EXTENSION ::= {
	{ ID id-GeographicalCoordinates	CRITICALITY ignore	EXTENSION GeographicalCoordinates PRESENCE optional}|
	{ ID id-MobileAccessPointLocation	CRITICALITY ignore EXTENSION Mobile-TRP-LocationInformation	PRESENCE optional }|
	{ ID id-MeasuredResultsAssociatedInfoList		CRITICALITY ignore	EXTENSION MeasuredResultsAssociatedInfoList		PRESENCE optional},
	...
}

E-CID-AoA-NR-per-TRP ::= SEQUENCE (SIZE (1..maxNoOfMeasTRPs)) OF E-CID-AoA-NR-per-TRP-Item

E-CID-AoA-NR-per-TRP-Item ::= SEQUENCE {
	tRP-ID							TRP-ID, 
	geographicalCoordinates			GeographicalCoordinates		OPTIONAL,
	uL-AngleOfArrival				UL-AoA,
	timeStamp						TimeStamp,
	measurementQuality				TrpMeasurementQuality		OPTIONAL,
	iE-Extensions					ProtocolExtensionContainer {{ E-CID-AoA-NR-per-TRP-Item-ExtIEs}}	OPTIONAL,
	...
}

E-CID-AoA-NR-per-TRP-Item-ExtIEs NRPPA-PROTOCOL-EXTENSION ::= {
	...
}


EUTRACellIdentifier ::= BIT STRING (SIZE (28))

EARFCN ::= INTEGER (0..262143, ...)

Expected-Value-AoA ::= INTEGER (0..3599)

Expected-Value-ZoA ::= INTEGER (0..1799)


-- F

-- G

GeographicalCoordinates ::= SEQUENCE {
	tRPPositionDefinitionType	TRPPositionDefinitionType,
	dLPRSResourceCoordinates	DLPRSResourceCoordinates	OPTIONAL,
	iE-Extensions				ProtocolExtensionContainer { { GeographicalCoordinates-ExtIEs } } OPTIONAL,
	...
}

GeographicalCoordinates-ExtIEs NRPPA-PROTOCOL-EXTENSION ::= {
	{ ID id-ARPLocationInfo		CRITICALITY ignore EXTENSION ARPLocationInformation 	PRESENCE optional},
	...
}


GNB-RxTxTimeDiff ::= SEQUENCE {

	rxTxTimeDiff		GNBRxTxTimeDiffMeas,
	additionalPathList	AdditionalPathList	OPTIONAL,
	iE-Extensions		ProtocolExtensionContainer { { GNB-RxTxTimeDiff-ExtIEs} }	OPTIONAL,
	...
}

GNB-RxTxTimeDiff-ExtIEs NRPPA-PROTOCOL-EXTENSION ::= {
	{ ID id-ExtendedAdditionalPathList	CRITICALITY ignore EXTENSION ExtendedAdditionalPathList PRESENCE optional}|
	{ ID id-TRPTEGInformation		CRITICALITY ignore EXTENSION TRPTEGInformation	PRESENCE optional },

	...
}


GNBRxTxTimeDiffMeas ::= CHOICE {
	k0			INTEGER (0.. 1970049),
	k1			INTEGER (0.. 985025),
	k2			INTEGER (0.. 492513),
	k3			INTEGER (0.. 246257),
	k4			INTEGER (0.. 123129),
	k5			INTEGER (0.. 61565),
		choice-extension		ProtocolIE-Single-Container { { GNBRxTxTimeDiffMeas-ExtIEs } } 
	}
	
	GNBRxTxTimeDiffMeas-ExtIEs		NRPPA-PROTOCOL-IES ::= {
	{ID id-ReportingGranularitykminus1 	CRITICALITY ignore TYPE ReportingGranularitykminus1 PRESENCE mandatory}|
		{ID id-ReportingGranularitykminus2 	CRITICALITY ignore TYPE ReportingGranularitykminus2 PRESENCE mandatory}|
		{ID id-ReportingGranularitykminus3 	CRITICALITY ignore TYPE ReportingGranularitykminus3 PRESENCE mandatory}|
		{ID id-ReportingGranularitykminus4 	CRITICALITY ignore TYPE ReportingGranularitykminus4 PRESENCE mandatory}|
		{ID id-ReportingGranularitykminus5 	CRITICALITY ignore TYPE ReportingGranularitykminus5 PRESENCE mandatory}|
		{ID id-ReportingGranularitykminus6 	CRITICALITY ignore TYPE ReportingGranularitykminus6 PRESENCE mandatory},
		...
}

-- H

HESSID ::= OCTET STRING (SIZE(6))

-- I

Inferred-measurement ::= BIT STRING (SIZE (8))

-- J

-- K

-- L

LCS-to-GCS-Translation::= SEQUENCE {
	alpha				INTEGER (0..3599),
	beta				INTEGER (0..3599),
	gamma				INTEGER (0..3599),
	iE-Extensions		ProtocolExtensionContainer { { LCS-to-GCS-Translation-ExtIEs} } OPTIONAL,
	...
}

LCS-to-GCS-Translation-ExtIEs NRPPA-PROTOCOL-EXTENSION ::= {
	...
}

LCS-to-GCS-TranslationItem::= SEQUENCE {
	alpha				INTEGER (0..359),
	alphaFine			INTEGER (0..9) 		OPTIONAL,
	beta				INTEGER (0..359),
	betaFine			INTEGER (0..9) 		OPTIONAL,
	gamma				INTEGER (0..359),
	gammaFine			INTEGER (0..9) 		OPTIONAL,
	iE-Extensions		ProtocolExtensionContainer { { LCS-to-GCS-TranslationItem-ExtIEs} } OPTIONAL,
	...
}

LCS-to-GCS-TranslationItem-ExtIEs NRPPA-PROTOCOL-EXTENSION ::= {
	...
}

LocationUncertainty ::= SEQUENCE {
	horizontalUncertainty		INTEGER (0..255),
	horizontalConfidence		INTEGER (0..100),
	verticalUncertainty			INTEGER (0..255),
	verticalConfidence			INTEGER (0..100),
	iE-Extensions				ProtocolExtensionContainer { { LocationUncertainty-ExtIEs} } OPTIONAL,
	...
}

LocalOrigin ::= SEQUENCE {
	relativeCoordinateID			CoordinateID,
	horizontalAxesOrientation		INTEGER (0..3599),
	referencePointCoordinateHA		NGRANHighAccuracyAccessPointPosition	OPTIONAL,
	iE-Extensions				ProtocolExtensionContainer { { LocalOrigin-ExtIEs} } OPTIONAL,
	...
}

LocalOrigin-ExtIEs NRPPA-PROTOCOL-EXTENSION ::= {
	...
}

LocationUncertainty-ExtIEs NRPPA-PROTOCOL-EXTENSION ::= {
	...
}

LoS-NLoSIndicatorHard ::= ENUMERATED {nlos, los}

LoS-NLoSIndicatorSoft ::= INTEGER (0..10)

LoS-NLoSInformation ::= CHOICE {
	loS-NLoSIndicatorSoft		LoS-NLoSIndicatorSoft,
	loS-NLoSIndicatorHard		LoS-NLoSIndicatorHard,
	choice-Extension		ProtocolIE-Single-Container {{ LoS-NLoSInformation-ExtIEs}}

}

LoS-NLoSInformation-ExtIEs NRPPA-PROTOCOL-IES ::= {
	...
}


-- M

MeasBasedOnAggregatedResources ::= ENUMERATED { true, ... }

Measurement-ID ::= INTEGER (1.. 65536, ...)

MeasurementAmount  ::= ENUMERATED {ma0, ma1, ma2, ma4, ma8, ma16, ma32, ma64}

MeasurementBeamInfoRequest ::= ENUMERATED {true, ...}

MeasurementBeamInfo ::= SEQUENCE {
	pRS-Resource-ID				PRS-Resource-ID		OPTIONAL,
	pRS-Resource-Set-ID			PRS-Resource-Set-ID	OPTIONAL,
	sSB-Index					SSB-Index			OPTIONAL,
	iE-Extensions								ProtocolExtensionContainer { { MeasurementBeamInfo-ExtIEs} } OPTIONAL,
	...
}

MeasurementBeamInfo-ExtIEs NRPPA-PROTOCOL-EXTENSION ::= {
	...
}


MeasurementPeriodicity ::= ENUMERATED {
	ms120,
	ms240,
	ms480,
	ms640,
	ms1024,
	ms2048,
	ms5120,
	ms10240,
	min1,
	min6,
	min12,
	min30,
	min60,
	...,
	ms20480,
	ms40960,
	extended
}

MeasurementPeriodicityExtended ::= ENUMERATED {
	ms160,
	ms320,
	ms1280,
	ms2560,
	ms61440,
	ms81920,
	ms368640,
	ms737280,
	ms1843200,
	...

}

MeasurementPeriodicityNR-AoA ::= ENUMERATED {
	ms160,
	ms320,
	ms640,
	ms1280,
	ms2560,
	ms5120,
	ms10240,
	ms20480,
	ms40960,
	ms61440,
	ms81920,
	ms368640,
	ms737280,
	ms1843200,
	...

}

MeasurementQuantities ::= SEQUENCE (SIZE (1.. maxNoMeas)) OF ProtocolIE-Single-Container { {MeasurementQuantities-ItemIEs} }

MeasurementQuantities-ItemIEs NRPPA-PROTOCOL-IES ::= {
	{ ID id-MeasurementQuantities-Item	CRITICALITY reject	TYPE MeasurementQuantities-Item		PRESENCE mandatory}
}

MeasurementQuantities-Item ::= SEQUENCE {
	measurementQuantitiesValue					MeasurementQuantitiesValue,
	iE-Extensions								ProtocolExtensionContainer { { MeasurementQuantitiesValue-ExtIEs} } OPTIONAL,
	...
}

MeasurementQuantitiesValue-ExtIEs NRPPA-PROTOCOL-EXTENSION ::= {
	...
}

MeasurementQuantitiesValue ::= ENUMERATED {
	cell-ID,
	angleOfArrival,
	timingAdvanceType1,
	timingAdvanceType2,
	rSRP,
	rSRQ,
	... ,
	sS-RSRP,
	sS-RSRQ,
	cSI-RSRP,
	cSI-RSRQ,
	angleOfArrivalNR,
	timingAdvanceNR,
	uE-Rx-Tx-Time-Diff,
	angleOfArrivalNR-per-TRP
}

MeasurementTimeOccasion ::= ENUMERATED {o1, o4, ...}

MeasurementCharacteristicsRequestIndicator ::= BIT STRING (SIZE (16))

MeasuredResults ::= SEQUENCE (SIZE (1.. maxNoMeas)) OF MeasuredResultsValue

MeasuredResultsAssociatedInfoList ::= SEQUENCE (SIZE (1..maxNoMeas)) OF MeasuredResultsAssociatedInfoItem

MeasuredResultsAssociatedInfoItem ::= SEQUENCE {
	timeStamp					TimeStamp				OPTIONAL,
	measurementQuality			TrpMeasurementQuality	OPTIONAL,
	iE-Extensions				ProtocolExtensionContainer { { MeasuredResultsAssociatedInfoItem-ExtIEs} } OPTIONAL,
	...
}

MeasuredResultsAssociatedInfoItem-ExtIEs NRPPA-PROTOCOL-EXTENSION ::= {
	{ ID id-DL-reference-signal-UERxTx-TD	CRITICALITY ignore	EXTENSION DL-reference-signal-UERxTx-TD PRESENCE optional},
	...
}

MeasuredResultsValue ::= CHOICE { 
	valueAngleOfArrival-EUTRA				INTEGER (0..719),
	valueTimingAdvanceType1-EUTRA			INTEGER (0..7690),
	valueTimingAdvanceType2-EUTRA			INTEGER (0..7690),
	resultRSRP-EUTRA						ResultRSRP-EUTRA,
	resultRSRQ-EUTRA						ResultRSRQ-EUTRA,
	choice-Extension			ProtocolIE-Single-Container {{ MeasuredResultsValue-ExtensionIE }}
}

MeasuredResultsValue-ExtensionIE NRPPA-PROTOCOL-IES ::= {
{ ID id-ResultSS-RSRP		CRITICALITY ignore	TYPE ResultSS-RSRP		PRESENCE mandatory	}|
	{ ID id-ResultSS-RSRQ		CRITICALITY ignore	TYPE ResultSS-RSRQ		PRESENCE mandatory	}|
	{ ID id-ResultCSI-RSRP		CRITICALITY ignore	TYPE ResultCSI-RSRP		PRESENCE mandatory	}|
	{ ID id-ResultCSI-RSRQ		CRITICALITY ignore	TYPE ResultCSI-RSRQ		PRESENCE mandatory	}|
	{ ID id-AngleOfArrivalNR	CRITICALITY ignore	TYPE UL-AoA				PRESENCE mandatory	}|
	{ ID id-NR-TADV				CRITICALITY ignore	TYPE NR-TADV			PRESENCE mandatory	}|
	{ ID id-UE-Rx-Tx-Time-Diff 	CRITICALITY ignore	TYPE UE-Rx-Tx-Time-Diff PRESENCE mandatory	}|
	{ ID id-E-CID-AoA-NR-per-TRP CRITICALITY ignore	TYPE E-CID-AoA-NR-per-TRP		PRESENCE mandatory	},
	...
}

Mobile-TRP-LocationInformation ::= SEQUENCE {
	location-Information			OCTET STRING,
	velocity-Information			OCTET STRING	OPTIONAL,
	location-time-stamp				TimeStamp	OPTIONAL,
	iE-Extensions					ProtocolExtensionContainer { { Mobile-TRP-LocationInformation-ExtIEs} } OPTIONAL,
	...
}

Mobile-TRP-LocationInformation-ExtIEs NRPPA-PROTOCOL-EXTENSION ::= {
	...
}

Mobile-IAB-MT-UE-ID ::= OCTET STRING

MultipleULAoA ::= SEQUENCE {
	multipleULAoA					MultipleULAoA-List,
	iE-Extensions					ProtocolExtensionContainer { { MultipleULAoA-ExtIEs} } OPTIONAL,
	...
}

MultipleULAoA-ExtIEs NRPPA-PROTOCOL-EXTENSION ::= {
	...
}

MultipleULAoA-List ::= SEQUENCE (SIZE(1.. maxnoofULAoAs)) OF MultipleULAoA-Item

MultipleULAoA-Item ::= CHOICE {	
	uL-AoA		UL-AoA,
	ul-ZoA		ZoA,
	choice-extension ProtocolIE-Single-Container { { MultipleULAoA-Item-ExtIEs } }
}

MultipleULAoA-Item-ExtIEs NRPPA-PROTOCOL-IES ::= {
	...
}

MeasuredFrequencyHops ::= ENUMERATED {singleHop, multiHop, ...}

-- N

NarrowBandIndex ::= INTEGER (0..15,...)

NG-RANAccessPointPosition ::= SEQUENCE {
	latitudeSign				ENUMERATED {north, south},
	latitude					INTEGER (0..8388607),
	longitude					INTEGER (-8388608..8388607),
	directionOfAltitude			ENUMERATED {height, depth},
	altitude					INTEGER (0..32767),
	uncertaintySemi-major		INTEGER (0..127),
	uncertaintySemi-minor		INTEGER (0..127),
	orientationOfMajorAxis		INTEGER (0..179),
	uncertaintyAltitude			INTEGER (0..127),
	confidence					INTEGER (0..100),
	iE-Extensions				ProtocolExtensionContainer { { NG-RANAccessPointPosition-ExtIEs} } OPTIONAL,
	...
}

NG-RANAccessPointPosition-ExtIEs NRPPA-PROTOCOL-EXTENSION ::= {
	...
}

NGRANHighAccuracyAccessPointPosition ::= SEQUENCE {
	latitude					INTEGER (-2147483648.. 2147483647),
	longitude					INTEGER (-2147483648.. 2147483647),
	altitude					INTEGER (-64000..1280000),
	uncertaintySemi-major		INTEGER (0..255),
	uncertaintySemi-minor		INTEGER (0..255),
	orientationOfMajorAxis		INTEGER (0..179),
	horizontalConfidence		INTEGER (0..100),
	uncertaintyAltitude			INTEGER (0..255),
	verticalConfidence			INTEGER (0..100), 
	iE-Extensions				ProtocolExtensionContainer { { NGRANHighAccuracyAccessPointPosition-ExtIEs} } OPTIONAL,
	...
}

NGRANHighAccuracyAccessPointPosition-ExtIEs NRPPA-PROTOCOL-EXTENSION ::= {
	...
}

NG-RAN-CGI ::= SEQUENCE {
	pLMN-Identity				PLMN-Identity,
	nG-RANcell		NG-RANCell,
	iE-Extensions				ProtocolExtensionContainer { {NG-RAN-CGI-ExtIEs} } OPTIONAL,
	...
}

NG-RAN-CGI-ExtIEs NRPPA-PROTOCOL-EXTENSION ::= {
	...
}

NG-RANCell ::= CHOICE {
	eUTRA-CellID	EUTRACellIdentifier,
	nR-CellID		NRCellIdentifier,
	choice-Extension			ProtocolIE-Single-Container {{ NG-RANCell-ExtensionIE }}
}

NG-RANCell-ExtensionIE NRPPA-PROTOCOL-IES ::= {
	...
}

NR-ARFCN ::= INTEGER (0..3279165)

NRCellIdentifier ::= BIT STRING (SIZE (36)) 

NrofSymbolsExtended ::=  ENUMERATED {n8, n10, n12, n14, ...}

NR-PCI ::= INTEGER (0..1007)

NR-PRS-Beam-Information ::= SEQUENCE {
	nR-PRS-Beam-InformationList SEQUENCE (SIZE(1.. maxPRS-ResourceSets)) OF NR-PRS-Beam-InformationItem,
	lCS-to-GCS-TranslationList SEQUENCE (SIZE(1..maxnolcs-gcs-translation)) OF LCS-to-GCS-TranslationItem		OPTIONAL,
	iE-Extensions	ProtocolExtensionContainer { { NR-PRS-Beam-Information-IEs} } OPTIONAL,
 	...
}

NR-PRS-Beam-Information-IEs NRPPA-PROTOCOL-EXTENSION ::= { 
 ...
}

NR-PRS-Beam-InformationItem ::= SEQUENCE {
	pRSresourceSetID 	PRS-Resource-Set-ID,
	pRSAngle 		SEQUENCE (SIZE(1..maxPRS-ResourcesPerSet)) OF PRSAngleItem,
	iE-Extensions	ProtocolExtensionContainer { { NR-PRS-Beam-InformationItem-ExtIEs} } OPTIONAL,
	...
}

NR-PRS-Beam-InformationItem-ExtIEs NRPPA-PROTOCOL-EXTENSION ::= { 
 ...
}

NR-TADV ::= INTEGER (0.. 7690)

NumberOfAntennaPorts-EUTRA ::= ENUMERATED {
		n1-or-n2,
		n4,
		...
}

NumberOfDlFrames-EUTRA ::= ENUMERATED {
		sf1,
		sf2,
		sf4,
		sf6,
		...
}

NumberOfDlFrames-Extended-EUTRA ::= INTEGER (1..160,...)

NumberOfFrequencyHoppingBands ::= ENUMERATED {
	twobands,
	fourbands,
	...
}

NumberOfTRPRxTEG ::= ENUMERATED {two, three, four, six, eight, ...}

NumberOfTRPRxTxTEG ::= ENUMERATED {two, three, four, six, eight, ...}

NZP-CSI-RS-ResourceID::= INTEGER  (0..191)

-- O

OnDemandPRS-Info ::= SEQUENCE {
	onDemandPRSRequestAllowed				BIT STRING (SIZE (16)),
	allowedResourceSetPeriodicityValues		BIT STRING (SIZE (24))	OPTIONAL,
	allowedPRSBandwidthValues				BIT STRING (SIZE (64))	OPTIONAL,
	allowedResourceRepetitionFactorValues	BIT STRING (SIZE (8))	OPTIONAL,
	allowedResourceNumberOfSymbolsValues	BIT STRING (SIZE (8))	OPTIONAL,
	allowedCombSizeValues					BIT STRING (SIZE (8))	OPTIONAL,
	iE-Extensions	ProtocolExtensionContainer { { OnDemandPRS-Info-ExtIEs} } OPTIONAL,
	...
}

OnDemandPRS-Info-ExtIEs NRPPA-PROTOCOL-EXTENSION ::= {
	...
}

OTDOACells ::= SEQUENCE (SIZE (1.. maxCellinRANnode)) OF SEQUENCE {
	oTDOACellInfo					OTDOACell-Information,
	iE-Extensions					ProtocolExtensionContainer { {OTDOACells-ExtIEs} } OPTIONAL,
	...
}

OTDOACells-ExtIEs NRPPA-PROTOCOL-EXTENSION ::= {
	...
}

OTDOACell-Information ::= SEQUENCE (SIZE (1..maxnoOTDOAtypes)) OF OTDOACell-Information-Item

OTDOACell-Information-Item ::= CHOICE {
	pCI-EUTRA									PCI-EUTRA,
	cGI-EUTRA									CGI-EUTRA,
	tAC											TAC,
	eARFCN										EARFCN,
	pRS-Bandwidth-EUTRA							PRS-Bandwidth-EUTRA,
	pRS-ConfigurationIndex-EUTRA				PRS-ConfigurationIndex-EUTRA, 
	cPLength-EUTRA								CPLength-EUTRA,
	numberOfDlFrames-EUTRA						NumberOfDlFrames-EUTRA,
	numberOfAntennaPorts-EUTRA					NumberOfAntennaPorts-EUTRA,
	sFNInitialisationTime-EUTRA					SFNInitialisationTime-EUTRA,
	nG-RANAccessPointPosition					NG-RANAccessPointPosition,
	pRSMutingConfiguration-EUTRA				PRSMutingConfiguration-EUTRA,
	prsid-EUTRA									PRS-ID-EUTRA,
	tpid-EUTRA									TP-ID-EUTRA,
	tpType-EUTRA								TP-Type-EUTRA,
	numberOfDlFrames-Extended-EUTRA				NumberOfDlFrames-Extended-EUTRA,
	crsCPlength-EUTRA							CPLength-EUTRA,
	dL-Bandwidth-EUTRA							DL-Bandwidth-EUTRA,
	pRSOccasionGroup-EUTRA						PRSOccasionGroup-EUTRA,
	pRSFrequencyHoppingConfiguration-EUTRA		PRSFrequencyHoppingConfiguration-EUTRA,
	choice-Extension		ProtocolIE-Single-Container {{ OTDOACell-Information-Item-ExtensionIE }}
}

OTDOACell-Information-Item-ExtensionIE NRPPA-PROTOCOL-IES ::= {
	{ ID id-TDD-Config-EUTRA-Item		CRITICALITY 	ignore	TYPE 	TDD-Config-EUTRA-Item			PRESENCE 	mandatory }|
	{ ID id-CGI-NR						CRITICALITY 	ignore	TYPE 	CGI-NR							PRESENCE 	mandatory }|
	{ ID id-SFNInitialisationTime-NR	CRITICALITY 	ignore	TYPE 	SFNInitialisationTime-EUTRA 	PRESENCE 	mandatory },
	...
}

OTDOA-Information-Item ::= ENUMERATED {
		pci,
		cGI,
		tac,
		earfcn,
		prsBandwidth,
		prsConfigIndex,
		cpLength,
		noDlFrames,
		noAntennaPorts,
		sFNInitTime,
		nG-RANAccessPointPosition,
		prsmutingconfiguration,
		prsid,
		tpid,
		tpType,
		crsCPlength,
		dlBandwidth, 
		multipleprsConfigurationsperCell,
		prsOccasionGroup,
		prsFrequencyHoppingConfiguration,
		...,
		tddConfig
}

OtherRATMeasurementQuantities ::= SEQUENCE (SIZE (0.. maxNoMeas)) OF ProtocolIE-Single-Container { {OtherRATMeasurementQuantities-ItemIEs} }

OtherRATMeasurementQuantities-ItemIEs NRPPA-PROTOCOL-IES ::= {
	{ ID id-OtherRATMeasurementQuantities-Item	CRITICALITY reject	TYPE OtherRATMeasurementQuantities-Item PRESENCE mandatory}}

OtherRATMeasurementQuantities-Item ::= SEQUENCE {
	otherRATMeasurementQuantitiesValue			OtherRATMeasurementQuantitiesValue,
	iE-Extensions								ProtocolExtensionContainer { { OtherRATMeasurementQuantitiesValue-ExtIEs} } OPTIONAL,
	...
}

OtherRATMeasurementQuantitiesValue-ExtIEs NRPPA-PROTOCOL-EXTENSION ::= {
	...
}

OtherRATMeasurementQuantitiesValue ::= ENUMERATED {
	geran,
	utran,
	... ,
	nR,
	eUTRA
}

OtherRATMeasurementResult ::= SEQUENCE (SIZE (1.. maxNoMeas)) OF OtherRATMeasuredResultsValue

OtherRATMeasuredResultsValue ::= CHOICE {
	resultGERAN									ResultGERAN,
	resultUTRAN									ResultUTRAN,
	choice-Extension		ProtocolIE-Single-Container {{ OtherRATMeasuredResultsValue-ExtensionIE }}
}


OtherRATMeasuredResultsValue-ExtensionIE NRPPA-PROTOCOL-IES ::= {
	{ ID id-ResultNR		CRITICALITY 	ignore	TYPE 	ResultNR		PRESENCE 	mandatory }|
	{ ID id-ResultEUTRA		CRITICALITY 	ignore	TYPE 	ResultEUTRA		PRESENCE 	mandatory },
	...
}

Outcome ::= ENUMERATED {
		failed,
		...
}


-- P

PathlossReferenceInformation ::= SEQUENCE {
	pathlossReferenceSignal					PathlossReferenceSignal,
	iE-Extensions					ProtocolExtensionContainer { { PathlossReferenceInformation-ExtIEs } } OPTIONAL,
	...
}

PathlossReferenceInformation-ExtIEs NRPPA-PROTOCOL-EXTENSION ::= {
	...
} 


PathlossReferenceSignal ::= CHOICE { 
	sSB-Reference					SSB,
	dL-PRS-Reference				DL-PRS,
	choice-Extension				ProtocolIE-Single-Container {{ PathlossReferenceSignal-ExtensionIE }}
}

PathlossReferenceSignal-ExtensionIE NRPPA-PROTOCOL-IES ::= {
	...
}


PCI-EUTRA ::= INTEGER (0..503, ...)

PhysCellIDGERAN ::= INTEGER (0..63, ...)

PhysCellIDUTRA-FDD ::= INTEGER (0..511, ...)

PhysCellIDUTRA-TDD ::= INTEGER (0..127, ...)

PLMN-Identity ::= OCTET STRING (SIZE(3))

PeriodicityList ::= SEQUENCE (SIZE (1.. maxnoSRS-ResourcePerSet)) OF PeriodicityItem

PeriodicityItem ::= ENUMERATED {ms0dot125, ms0dot25, ms0dot5, ms0dot625, ms1, ms1dot25, ms2, ms2dot5, ms4dot, ms5, ms8, ms10, ms16, ms20, ms32, ms40, ms64, ms80m, ms160, ms320, ms640m, ms1280, ms2560, ms5120, ms10240, ...}


PosSIBs ::= SEQUENCE (SIZE (1.. maxNrOfPosSIBs)) OF SEQUENCE {
	posSIB-Type						PosSIB-Type,
	posSIB-Segments					PosSIB-Segments,
	assistanceInformationMetaData	AssistanceInformationMetaData	OPTIONAL,
	broadcastPriority				INTEGER (1..16,...)				OPTIONAL,
	iE-Extensions					ProtocolExtensionContainer { { PosSIBs-ExtIEs} }	OPTIONAL,
	...
}

PosSIBs-ExtIEs NRPPA-PROTOCOL-EXTENSION ::= {
	...
}

PosSIB-Segments ::= SEQUENCE (SIZE (1.. maxNrOfSegments)) OF SEQUENCE {
	assistanceDataSIBelement			OCTET STRING,
	iE-Extensions						ProtocolExtensionContainer { { PosSIB-Segments-ExtIEs} }	OPTIONAL,
	...
}

PosSIB-Segments-ExtIEs NRPPA-PROTOCOL-EXTENSION ::= {
	...
}

PosSIB-Type ::= ENUMERATED {
	posSibType1-1, 
	posSibType1-2, 
	posSibType1-3, 
	posSibType1-4, 
	posSibType1-5,
	posSibType1-6, 
	posSibType1-7,
	posSibType1-8, 
	posSibType2-1, 
	posSibType2-2, 
	posSibType2-3,
	posSibType2-4, 
	posSibType2-5, 
	posSibType2-6, 
	posSibType2-7, 
	posSibType2-8,
	posSibType2-9, 
	posSibType2-10, 
	posSibType2-11, 
	posSibType2-12, 
	posSibType2-13, 
	posSibType2-14, 
	posSibType2-15, 
	posSibType2-16,
	posSibType2-17, 
	posSibType2-18, 
	posSibType2-19, 
	posSibType2-20, 
	posSibType2-21, 
	posSibType2-22, 
	posSibType2-23,
	posSibType2-24,
	posSibType2-25, 
	posSibType3-1, 
	posSibType4-1,
	posSibType5-1,
	posSibType6-1,  
	posSibType6-2,
	posSibType6-3,  
	...,
	posSibType1-9,
	posSibType1-10,
	posSibType6-4, 
	posSibType6-5, 
	posSibType6-6,
	posSibType1-11, 
	posSibType1-12,
	posSibType2-17a,
	posSibType2-18a,
	posSibType2-20a,
	posSibType2-26,
	posSibType2-27,
	posSibType6-7,
	posSibType7-1,
	posSibType7-2,
	posSibType7-3,
	posSibType7-4  
}

PositioningDataInformation ::= SEQUENCE {
	tRP-Measurement-List		TRP-Measurement-List,
	iE-extensions				ProtocolExtensionContainer { { TRP-Measurement-List-ExtIEs} } OPTIONAL,
	...
}

TRP-Measurement-List-ExtIEs NRPPA-PROTOCOL-EXTENSION ::= {
	...
}

TRP-Measurement-List ::= SEQUENCE (SIZE (1..maxNoOfMeasTRPs)) OF TRP-Measurement-Item
TRP-Measurement-Item ::= SEQUENCE {
	tRP-ID				TRP-ID, 
	uL-RTOA				UL-RTOAMeasurement	OPTIONAL,
	gNB-RxTxTimeDiff	GNB-RxTxTimeDiff	OPTIONAL,
	los-nlos-info		LoS-NLoSInformation	OPTIONAL,
	timeStamp			TimeStamp,
	measurementQuality	TrpMeasurementQuality	OPTIONAL,
	iE-extensions		ProtocolExtensionContainer { { TRP-Measurement-Item-ExtIEs } } OPTIONAL,
	...
}

TRP-Measurement-Item-ExtIEs NRPPA-PROTOCOL-EXTENSION ::= {
	...
}

PositioningDataUnavailable ::= ENUMERATED {
	not-supported,
	not-available,
	...}

PositioningDataCollectionNeeded ::= SEQUENCE {
	requested-PosDataCollection 		BIT STRING (SIZE(8)), 
	iE-extensions		ProtocolExtensionContainer { { PositioningDataCollectionNeeded-ExtIEs } } OPTIONAL,
	...
}

PositioningDataCollectionNeeded-ExtIEs NRPPA-PROTOCOL-EXTENSION ::= {
	...
}

PRSBWAggregationRequestInfoList ::= SEQUENCE (SIZE (1..maxnoAggCombinations)) OF PRSBWAggregationRequestInfo-Item

PRSBWAggregationRequestInfo-Item ::= SEQUENCE {
	dl-PRSBWAggregationRequestInfo-List	DL-PRSBWAggregationRequestInfo-List,
	iE-Extensions						ProtocolExtensionContainer { { PRSBWAggregationRequestInfo-Item-ExtIEs} } OPTIONAL,
	...
}

PRSBWAggregationRequestInfo-Item-ExtIEs NRPPA-PROTOCOL-EXTENSION ::= {
	...
}

DL-PRSBWAggregationRequestInfo-List ::= SEQUENCE (SIZE (2..maxnoAggPosPRSResourceSets)) OF DL-PRSBWAggregationRequestInfo-Item

DL-PRSBWAggregationRequestInfo-Item ::= SEQUENCE {
	dl-prs-ResourceSetIndex				INTEGER (1..8),
	iE-Extensions						ProtocolExtensionContainer { {DL-PRSBWAggregationRequestInfo-Item-ExtIEs} } OPTIONAL,
	...
}

DL-PRSBWAggregationRequestInfo-Item-ExtIEs NRPPA-PROTOCOL-EXTENSION ::= {
	...
}

PosSRSResource-List ::= SEQUENCE (SIZE (1..maxnoSRS-PosResources)) OF PosSRSResource-Item

PosSRSResource-Item ::= SEQUENCE {
	srs-PosResourceId				SRSPosResourceID,
	transmissionCombPos				TransmissionCombPos,
	startPosition                   INTEGER (0..13),
	nrofSymbols                     ENUMERATED {n1, n2, n4, n8, n12},
	freqDomainShift                 INTEGER (0..268),
	c-SRS	                        INTEGER (0..63),
	groupOrSequenceHopping          ENUMERATED { neither, groupHopping, sequenceHopping },
	resourceTypePos					ResourceTypePos,
	sequenceId                      INTEGER (0.. 65535),
	spatialRelationPos				SpatialRelationPos OPTIONAL,
	iE-Extensions		ProtocolExtensionContainer { { PosSRSResource-Item-ExtIEs} }	OPTIONAL,
	...
}

PosSRSResource-Item-ExtIEs NRPPA-PROTOCOL-EXTENSION ::= {
	{ ID id-TxHoppingConfiguration	CRITICALITY ignore	EXTENSION TxHoppingConfiguration	PRESENCE optional},
	...
}


PosSRSResourceID-List ::= SEQUENCE (SIZE (1..maxnoSRS-PosResources)) OF SRSPosResourceID

PosSRSResourceSet-List ::= SEQUENCE (SIZE (1..maxnoSRS-PosResourceSets)) OF PosSRSResourceSet-Item

PosSRSResourceIDPerSet-List ::= SEQUENCE (SIZE (1..maxnoSRS-PosResourcePerSet)) OF SRSPosResourceID
 

PosSRSResourceSet-Item ::= SEQUENCE {
	possrsResourceSetID				INTEGER(0..15),
	possRSResourceIDPerSet-List		PosSRSResourceIDPerSet-List,
	posresourceSetType				PosResourceSetType,
	iE-Extensions		ProtocolExtensionContainer { { PosSRSResourceSet-Item-ExtIEs} }	OPTIONAL,
	...
}

PosSRSResourceSet-Item-ExtIEs NRPPA-PROTOCOL-EXTENSION ::= {
	...
}

PosSRSResourceSet-Aggregation-List ::= SEQUENCE (SIZE (1..maxnoAggregatedPosSRSCombinations)) OF PosSRSResourceSet-Aggregation-Item
 

PosSRSResourceSet-Aggregation-Item ::= SEQUENCE {
	combined-posSRSResourceSet-List			Combined-PosSRSResourceSet-List,	iE-Extensions		ProtocolExtensionContainer { { PosSRSResourceSet-Aggregation-Item-ExtIEs} }	OPTIONAL,
	...
}

PosSRSResourceSet-Aggregation-Item-ExtIEs NRPPA-PROTOCOL-EXTENSION ::= {
	...
}


Combined-PosSRSResourceSet-List ::= SEQUENCE (SIZE (2..maxnoaggregatedPosSRS-ResourceSets)) OF Combined-PosSRSResourceSet-Item


Combined-PosSRSResourceSet-Item::= SEQUENCE {
	pointA				INTEGER (0..3279165),
	pCI-NR				INTEGER(0..1007)		OPTIONAL,
	possrsResourceSetID	INTEGER(0..15),
	scs-specificCarrier	SCS-SpecificCarrier,
	iE-Extensions						ProtocolExtensionContainer { { Combined-PosSRSResourceSet-Item-ExtIEs} } OPTIONAL,
	...
}

Combined-PosSRSResourceSet-Item-ExtIEs NRPPA-PROTOCOL-EXTENSION ::= {
	...
}


PosResourceSetType  ::= CHOICE {
	periodic			PosResourceSetTypePeriodic,
	semi-persistent		PosResourceSetTypeSemi-persistent,
	aperiodic			PosResourceSetTypeAperiodic,
	choice-extension				ProtocolIE-Single-Container {{ PosResourceSetType-ExtIEs }}
}

PosResourceSetType-ExtIEs NRPPA-PROTOCOL-IES ::= {
	...
}

PosResourceSetTypePeriodic ::= SEQUENCE {
	posperiodicSet			ENUMERATED{true, ...},
	iE-Extensions		ProtocolExtensionContainer { { PosResourceSetTypePeriodic-ExtIEs} }	OPTIONAL,
	...
}

PosResourceSetTypePeriodic-ExtIEs NRPPA-PROTOCOL-EXTENSION ::= {
	...
}

PosResourceSetTypeSemi-persistent ::= SEQUENCE {
possemi-persistentSet	ENUMERATED{true, ...},
	iE-Extensions		ProtocolExtensionContainer { { PosResourceSetTypeSemi-persistent-ExtIEs} }	OPTIONAL,
	...
}

PosResourceSetTypeSemi-persistent-ExtIEs NRPPA-PROTOCOL-EXTENSION ::= {
	...
}

PosResourceSetTypeAperiodic ::= SEQUENCE {
	sRSResourceTrigger		 	INTEGER(1..3),
	iE-Extensions				ProtocolExtensionContainer { { PosResourceSetTypeAperiodic-ExtIEs} }	OPTIONAL,
	...
}

PosResourceSetTypeAperiodic-ExtIEs NRPPA-PROTOCOL-EXTENSION ::= {
	...
}

PreconfigurationResult ::= BIT STRING (SIZE(8))

PRS-Bandwidth-EUTRA ::= ENUMERATED {
		bw6,
		bw15,
		bw25,
		bw50,
		bw75,
		bw100,
		...
}


PRSAngleItem  ::= SEQUENCE {
	nRPRSAzimuth			INTEGER (0..359),
	nRPRSAzimuthFine		INTEGER (0..9) OPTIONAL,
	nRPRSElevation			INTEGER (0..180) OPTIONAL,
	nRPRSElevationFine		INTEGER (0..9) OPTIONAL,
	iE-Extensions			ProtocolExtensionContainer { { PRSAngleItem-ExtIEs} } OPTIONAL,
	...
}

PRSAngleItem-ExtIEs NRPPA-PROTOCOL-EXTENSION ::= {
	{ ID id-PRS-Resource-ID		CRITICALITY ignore EXTENSION PRS-Resource-ID		PRESENCE optional },
	...
}

PRSInformationPos  ::= SEQUENCE {
	pRS-IDPos					PRS-ID,	
	pRS-Resource-Set-IDPos		PRS-Resource-Set-ID,
	pRS-Resource-IDPos			PRS-Resource-ID	OPTIONAL,
	iE-Extensions					ProtocolExtensionContainer { { PRSInformationPos-ExtIEs} } OPTIONAL,
	...
}

PRSInformationPos-ExtIEs NRPPA-PROTOCOL-EXTENSION ::= {
	...
}

PRSConfigRequestType ::= ENUMERATED {configure, off, ...}

PRSConfiguration ::= SEQUENCE {
	pRSResourceSet-List				PRSResourceSet-List,	
	iE-Extensions					ProtocolExtensionContainer { { PRSConfiguration-ExtIEs} } OPTIONAL,
	...
}

PRSConfiguration-ExtIEs NRPPA-PROTOCOL-EXTENSION ::= {
	{ ID id-AggregatedPRSResourceSetList	CRITICALITY 	ignore	EXTENSION AggregatedPRSResourceSetList 	PRESENCE 	optional },
	...
}


PRS-ConfigurationIndex-EUTRA ::= INTEGER (0..4095, ...)

PRS-ID-EUTRA	::= INTEGER (0..4095, ...)

PRSMutingConfiguration-EUTRA ::= CHOICE {
	two 												BIT STRING (SIZE (2)),
	four 												BIT STRING (SIZE (4)),
	eight 												BIT STRING (SIZE (8)),
	sixteen 											BIT STRING (SIZE (16)),
	thirty-two											BIT STRING (SIZE (32)),
	sixty-four											BIT STRING (SIZE (64)),
	one-hundred-and-twenty-eight						BIT STRING (SIZE (128)),
	two-hundred-and-fifty-six							BIT STRING (SIZE (256)),
	five-hundred-and-twelve								BIT STRING (SIZE (512)),
	one-thousand-and-twenty-four						BIT STRING (SIZE (1024)),
	choice-Extension			ProtocolIE-Single-Container {{ PRSMutingConfiguration-EUTRA-ExtensionIE }}
}

PRSMutingConfiguration-EUTRA-ExtensionIE NRPPA-PROTOCOL-IES ::= {
	...
}

PRSOccasionGroup-EUTRA ::= ENUMERATED {
	og2,
	og4,
	og8,
	og16,
	og32,
	og64,
	og128,
	...
}

PRSFrequencyHoppingConfiguration-EUTRA ::= SEQUENCE {
	noOfFreqHoppingBands		NumberOfFrequencyHoppingBands,
	bandPositions				SEQUENCE(SIZE (1..maxnoFreqHoppingBandsMinusOne)) OF NarrowBandIndex,
	iE-Extensions				ProtocolExtensionContainer { { PRSFrequencyHoppingConfiguration-EUTRA-Item-IEs} } OPTIONAL,
	...
}

PRSFrequencyHoppingConfiguration-EUTRA-Item-IEs NRPPA-PROTOCOL-EXTENSION ::= {
	...
}

PRS-Measurements-Info-List ::= SEQUENCE (SIZE(1..maxFreqLayers)) OF PRS-Measurements-Info-List-Item

PRS-Measurements-Info-List-Item ::= SEQUENCE {
	pointA						INTEGER (0..3279165),
	measPRSPeriodicity			ENUMERATED {ms20, ms40, ms80, ms160, ...},
	measPRSOffset				INTEGER (0..159, ...),
	measurementPRSLength		ENUMERATED {ms1dot5, ms3, ms3dot5, ms4, ms5dot5, ms6, ms10, ms20},
	iE-Extensions	ProtocolExtensionContainer { { PRS-Measurements-Info-List-Item-ExtIEs} } OPTIONAL,
		...
}

PRS-Measurements-Info-List-Item-ExtIEs NRPPA-PROTOCOL-EXTENSION ::= {
	...
}


PRSMuting::= SEQUENCE {
	pRSMutingOption1			PRSMutingOption1		OPTIONAL,
	pRSMutingOption2			PRSMutingOption2		OPTIONAL,
	iE-Extensions					ProtocolExtensionContainer { { PRSMuting-ExtIEs} } OPTIONAL,
	...
}
PRSMuting-ExtIEs NRPPA-PROTOCOL-EXTENSION ::= {
	...
}


PRSMutingOption1 ::= SEQUENCE {
	mutingPattern						DL-PRSMutingPattern,
	mutingBitRepetitionFactor			ENUMERATED{n1,n2,n4,n8,...},
	iE-Extensions					ProtocolExtensionContainer { { PRSMutingOption1-ExtIEs} } OPTIONAL,
	...
}
PRSMutingOption1-ExtIEs NRPPA-PROTOCOL-EXTENSION ::= {
	...
}

PRSMutingOption2 ::= SEQUENCE {
	mutingPattern						DL-PRSMutingPattern,
	iE-Extensions					ProtocolExtensionContainer { { PRSMutingOption2-ExtIEs} } OPTIONAL,
	...
}
PRSMutingOption2-ExtIEs NRPPA-PROTOCOL-EXTENSION ::= {
	...
}

PRSResource-List::= SEQUENCE (SIZE (1..maxnoofPRSresource)) OF PRSResource-Item

PRSResource-Item  ::= SEQUENCE {
	pRSResourceID			PRS-Resource-ID,
	sequenceID				INTEGER(0..4095),
	rEOffset				INTEGER(0..11,...),
	resourceSlotOffset		INTEGER(0..511),
	resourceSymbolOffset	INTEGER(0..12),
	qCLInfo					PRSResource-QCLInfo		OPTIONAL,
	iE-Extensions					ProtocolExtensionContainer { { PRSResource-Item-ExtIEs} } OPTIONAL,
	...
}
PRSResource-Item-ExtIEs NRPPA-PROTOCOL-EXTENSION ::= {
	{ ID id-ExtendedResourceSymbolOffset		CRITICALITY ignore EXTENSION ExtendedResourceSymbolOffset 	PRESENCE optional},
	...
}

ExtendedResourceSymbolOffset ::= INTEGER (0..13,...)

PRSResource-QCLInfo  ::= CHOICE {
	qCLSourceSSB		PRSResource-QCLSourceSSB,
	qCLSourcePRS		PRSResource-QCLSourcePRS,		
	choice-Extension		ProtocolIE-Single-Container {{ PRSResource-QCLInfo-ExtIEs }}
}

PRSResource-QCLInfo-ExtIEs NRPPA-PROTOCOL-IES ::= {
	...
}

PRSResource-QCLSourceSSB ::= SEQUENCE {
	pCI-NR				INTEGER(0..1007),
	sSB-Index 			SSB-Index	 OPTIONAL,		
	iE-Extensions		ProtocolExtensionContainer { { PRSResource-QCLSourceSSB-ExtIEs} } OPTIONAL,
	...
}

PRSResource-QCLSourceSSB-ExtIEs NRPPA-PROTOCOL-EXTENSION ::= {
	...
}

PRSResource-QCLSourcePRS ::= SEQUENCE {
	qCLSourcePRSResourceSetID		PRS-Resource-Set-ID,
	qCLSourcePRSResourceID 			PRS-Resource-ID OPTIONAL,		
	iE-Extensions					ProtocolExtensionContainer { { PRSResource-QCLSourcePRS-ExtIEs} } OPTIONAL,
	...
}
PRSResource-QCLSourcePRS-ExtIEs NRPPA-PROTOCOL-EXTENSION ::= {
	...
}



PRSResourceSet-List ::= SEQUENCE (SIZE (1..maxnoofPRSresourceSet)) OF PRSResourceSet-Item

PRSResourceSet-Item ::= SEQUENCE {
	pRSResourceSetID				PRS-Resource-Set-ID,
	subcarrierSpacing				ENUMERATED{kHz15, kHz30, kHz60, kHz120, ...},
	pRSbandwidth					INTEGER(1..63),
	startPRB						INTEGER(0..2176),
	pointA							INTEGER (0..3279165),
	combSize						ENUMERATED{n2, n4, n6, n12, ...},
	cPType							ENUMERATED{normal, extended, ...},
	resourceSetPeriodicity			ENUMERATED{n4,n5,n8,n10,n16,n20,n32,n40,n64,n80,n160,n320,n640,n1280,n2560,n5120,n10240,n20480,n40960, n81920,..., n128, n256, n512},
	resourceSetSlotOffset			INTEGER(0..81919,...),
	resourceRepetitionFactor		ENUMERATED{rf1,rf2,rf4,rf6,rf8,rf16,rf32,...},
	resourceTimeGap					ENUMERATED{tg1,tg2,tg4,tg8,tg16,tg32,...},
	resourceNumberofSymbols			ENUMERATED{n2,n4,n6,n12,...,n1},
	pRSMuting						PRSMuting 		OPTIONAL,
	pRSResourceTransmitPower		INTEGER(-60..50),
	pRSResource-List				PRSResource-List,	
	iE-Extensions					ProtocolExtensionContainer { { PRSResourceSet-Item-ExtIEs} } OPTIONAL,
	...
}

PRSResourceSet-Item-ExtIEs NRPPA-PROTOCOL-EXTENSION ::= {
	...
}

PRS-Resource-ID ::= INTEGER (0..63)

PRS-Resource-Set-ID ::= INTEGER(0..7)

PRS-ID ::= INTEGER(0..255)

PRSTransmissionOffIndication ::= CHOICE { 
	pRSTransmissionOffPerTRP				NULL,
	pRSTransmissionOffPerResourceSet		PRSTransmissionOffPerResourceSet,
	pRSTransmissionOffPerResource			PRSTransmissionOffPerResource,
	choice-Extension		ProtocolIE-Single-Container {{ PRSTransmissionOffIndication-ExtIEs }}
}

PRSTransmissionOffIndication-ExtIEs NRPPA-PROTOCOL-IES ::= {
	...
}

PRSTransmissionOffPerResource ::= SEQUENCE (SIZE (1..maxnoofPRSresourceSet)) OF PRSTransmissionOffPerResource-Item

PRSTransmissionOffPerResource-Item  ::= SEQUENCE {
	pRSResourceSetID								PRS-Resource-Set-ID,
	pRSTransmissionOffIndicationPerResourceList		SEQUENCE (SIZE(1.. maxnoofPRSresource)) OF PRSTransmissionOffIndicationPerResource-Item,
	iE-Extensions		ProtocolExtensionContainer { { PRSTransmissionOffPerResource-Item-ExtIEs} } OPTIONAL,
	...
}

PRSTransmissionOffPerResource-Item-ExtIEs NRPPA-PROTOCOL-EXTENSION ::= {
	...
}

PRSTransmissionOffIndicationPerResource-Item  ::= SEQUENCE {
	pRSResourceID		PRS-Resource-ID,
	iE-Extensions		ProtocolExtensionContainer { { PRSTransmissionOffIndicationPerResource-Item-ExtIEs} } OPTIONAL,
	...
}

PRSTransmissionOffIndicationPerResource-Item-ExtIEs NRPPA-PROTOCOL-EXTENSION ::= {
	...
}

PRSTransmissionOffInformation ::= SEQUENCE {
	pRSTransmissionOffIndication	PRSTransmissionOffIndication,
	iE-Extensions					ProtocolExtensionContainer { { PRSTransmissionOffInformation-ExtIEs} } OPTIONAL,
	...
}

PRSTransmissionOffInformation-ExtIEs NRPPA-PROTOCOL-EXTENSION ::= {
	...
}

PRSTransmissionOffPerResourceSet ::= SEQUENCE (SIZE (1..maxnoofPRSresourceSet)) OF PRSTransmissionOffPerResourceSet-Item

PRSTransmissionOffPerResourceSet-Item  ::= SEQUENCE {
	pRSResourceSetID		PRS-Resource-Set-ID,
	iE-Extensions			ProtocolExtensionContainer { { PRSTransmissionOffPerResourceSet-Item-ExtIEs} } OPTIONAL,
	...
}

PRSTransmissionOffPerResourceSet-Item-ExtIEs NRPPA-PROTOCOL-EXTENSION ::= {
	...
}

PRSTRPList ::= SEQUENCE (SIZE(1.. maxnoTRPs)) OF PRSTRPItem

PRSTRPItem ::= SEQUENCE {
		tRP-ID		TRP-ID,
		requestedDLPRSTransmissionCharacteristics	RequestedDLPRSTransmissionCharacteristics	OPTIONAL, 
-- The IE shall be present if the PRS Configuration Request Type IE is set to the value “configure” --
		pRSTransmissionOffInformation				PRSTransmissionOffInformation				OPTIONAL,
-- The IE shall be present if the PRS Configuration Request Type IE is set to the value “off” --
		iE-Extensions	ProtocolExtensionContainer { { PRSTRPItem-ExtIEs} } OPTIONAL,
		...
}

PRSTRPItem-ExtIEs NRPPA-PROTOCOL-EXTENSION ::= {
	...
}



PRSTransmissionTRPList ::= SEQUENCE (SIZE(1.. maxnoTRPs)) OF PRSTransmissionTRPItem

PRSTransmissionTRPItem ::= SEQUENCE {
		tRP-ID				TRP-ID,
		pRSConfiguration	PRSConfiguration, 
	iE-Extensions	ProtocolExtensionContainer { { PRSTransmissionTRPItem-ExtIEs} } OPTIONAL,
		...
}

PRSTransmissionTRPItem-ExtIEs NRPPA-PROTOCOL-EXTENSION ::= {
	...
}

PosValidityAreaCellList ::= SEQUENCE (SIZE (1..maxnoVACell)) OF PosValidityAreaCell-Item


PosValidityAreaCell-Item	::= SEQUENCE {
	nR-CGI				CGI-NR,
	nR-PCI				NR-PCI		OPTIONAL, 
	iE-Extensions		ProtocolExtensionContainer { { PosValidityAreaCell-Item-ExtIEs} }	OPTIONAL,
	...
}

PosValidityAreaCell-Item-ExtIEs NRPPA-PROTOCOL-EXTENSION ::= {
	...
}

PointA  ::= INTEGER (0..3279165)

-- Q

-- R

ReferenceSignal ::= CHOICE { 
	nZP-CSI-RS								NZP-CSI-RS-ResourceID,
	sSB										SSB,
	sRS										SRSResourceID,
	positioningSRS							SRSPosResourceID,
	dL-PRS									DL-PRS,
	choice-Extension				ProtocolIE-Single-Container {{ReferenceSignal-ExtensionIE }}
}

ReferenceSignal-ExtensionIE NRPPA-PROTOCOL-IES ::= {
	...
}

ReferencePoint ::= CHOICE {
	relativeCoordinateID			CoordinateID,
	referencePointCoordinate		NG-RANAccessPointPosition,
	referencePointCoordinateHA		NGRANHighAccuracyAccessPointPosition,
	choice-Extension				ProtocolIE-Single-Container { { ReferencePoint-ExtIEs} }
}

ReferencePoint-ExtIEs NRPPA-PROTOCOL-IES ::= {
{ID id-LocalOrigin	CRITICALITY ignore TYPE LocalOrigin PRESENCE mandatory},
	...
}

CoordinateID ::= INTEGER (0..511, ...)
RelativeGeodeticLocation ::= SEQUENCE { 
	milli-Arc-SecondUnits		ENUMERATED {zerodot03, zerodot3, three, ...},	heightUnits					ENUMERATED {mm, cm, m, ...}, 
	deltaLatitude				INTEGER (-1024.. 1023),
	deltaLongitude				INTEGER (-1024.. 1023),
	deltaHeight					INTEGER (-1024.. 1023),
	locationUncertainty			LocationUncertainty,
	iE-extensions						ProtocolExtensionContainer {{RelativeGeodeticLocation-ExtIEs }}	OPTIONAL,
	...
}

RelativeGeodeticLocation-ExtIEs NRPPA-PROTOCOL-EXTENSION ::= {
	...
}


RelativeCartesianLocation ::= SEQUENCE {
	xYZunit						ENUMERATED {mm, cm, dm, ...},
	xvalue						INTEGER (-65536..65535),
	yvalue						INTEGER (-65536..65535),
	zvalue						INTEGER (-32768..32767),
	locationUncertainty			LocationUncertainty,
	iE-Extensions				ProtocolExtensionContainer { { RelativeCartesianLocation-ExtIEs} } OPTIONAL,
	...
}

RelativeCartesianLocation-ExtIEs NRPPA-PROTOCOL-EXTENSION ::= {
	...
}

RelativePathDelay ::= CHOICE {
	k0			INTEGER(0..16351),
	k1			INTEGER(0..8176),
	k2			INTEGER(0..4088),
	k3			INTEGER(0..2044),
	k4			INTEGER(0..1022),
	k5			INTEGER(0..511),
	choice-Extension		ProtocolIE-Single-Container { { RelativePathDelay-ExtIEs} }
}

RelativePathDelay-ExtIEs NRPPA-PROTOCOL-IES ::= {
	{ID id-ReportingGranularitykminus1AdditionalPath 	CRITICALITY ignore TYPE ReportingGranularitykminus1AdditionalPath PRESENCE mandatory}|
	{ID id-ReportingGranularitykminus2AdditionalPath 	CRITICALITY ignore TYPE ReportingGranularitykminus2AdditionalPath PRESENCE mandatory}|
	{ID id-ReportingGranularitykminus3AdditionalPath 	CRITICALITY ignore TYPE ReportingGranularitykminus3AdditionalPath PRESENCE mandatory}|
	{ID id-ReportingGranularitykminus4AdditionalPath 	CRITICALITY ignore TYPE ReportingGranularitykminus4AdditionalPath PRESENCE mandatory}|
	{ID id-ReportingGranularitykminus5AdditionalPath 	CRITICALITY ignore TYPE ReportingGranularitykminus5AdditionalPath PRESENCE mandatory}|
	{ID id-ReportingGranularitykminus6AdditionalPath 	CRITICALITY ignore TYPE ReportingGranularitykminus6AdditionalPath PRESENCE mandatory},
	...
}

Remote-UE-Indication-Request ::= ENUMERATED {true, ...}

Remote-UE-Indication ::= ENUMERATED {l2-u2n-remote-ue, ...}

Remote-UE-Status ::= ENUMERATED {l2-u2n-remote-ue, no, ...}

RepetitionFactorExtended ::=  ENUMERATED {n3, n5, n6, n7, n8, n10, n12, n14, ...}

ReportCharacteristics ::= ENUMERATED {
	onDemand,
	periodic,
	...
}

ReportingGranularitykminus1 ::= INTEGER(0..3940097)ReportingGranularitykminus2 ::= INTEGER(0..7880193)
ReportingGranularitykminus3 ::= INTEGER(0..15760385)
ReportingGranularitykminus4 ::= INTEGER(0..31520769)
ReportingGranularitykminus5 ::= INTEGER(0..63041537)
ReportingGranularitykminus6 ::= INTEGER(0..126083073)

ReportingGranularitykminus1AdditionalPath ::= INTEGER(0..32701)
ReportingGranularitykminus2AdditionalPath ::= INTEGER(0..65401)
ReportingGranularitykminus3AdditionalPath ::= INTEGER(0..130801)
ReportingGranularitykminus4AdditionalPath ::= INTEGER(0..261601)
ReportingGranularitykminus5AdditionalPath ::= INTEGER(0..523201)
ReportingGranularitykminus6AdditionalPath ::= INTEGER(0..1046401)


RequestedDLPRSTransmissionCharacteristics ::= SEQUENCE {
	requestedDLPRSResourceSet-List		RequestedDLPRSResourceSet-List,
	numberofFrequencyLayers				INTEGER(1..4)			OPTIONAL,
	startTimeAndDuration				StartTimeAndDuration	OPTIONAL,
	iE-Extensions	ProtocolExtensionContainer { { RequestedDLPRSTransmissionCharacteristics-ExtIEs} } OPTIONAL,
	...
}

RequestedDLPRSTransmissionCharacteristics-ExtIEs NRPPA-PROTOCOL-EXTENSION ::= {
	{ ID id-PRSBWAggregationRequestInfoList	CRITICALITY ignore	EXTENSION PRSBWAggregationRequestInfoList	PRESENCE optional},
	...
}

RequestedDLPRSResourceSet-List ::= SEQUENCE (SIZE (1..maxnoofPRSresourceSet)) OF RequestedDLPRSResourceSet-Item

RequestedDLPRSResourceSet-Item ::= SEQUENCE {
	pRSbandwidth					INTEGER(1..63)	OPTIONAL,
	combSize						ENUMERATED{n2, n4, n6, n12, ...}	OPTIONAL,
	resourceSetPeriodicity			ENUMERATED{n4,n5,n8,n10,n16,n20,n32,n40,n64,n80,n160,n320,n640,n1280,n2560,n5120,n10240,n20480,n40960, n81920,..., n128, n256 ,n512}	OPTIONAL,
	resourceRepetitionFactor		ENUMERATED{rf1,rf2,rf4,rf6,rf8,rf16,rf32,...}		OPTIONAL,
	resourceNumberofSymbols			ENUMERATED{n2,n4,n6,n12,...,n1}						OPTIONAL,
	requestedDLPRSResource-List		RequestedDLPRSResource-List			OPTIONAL,
	resourceSetStartTimeAndDuration	StartTimeAndDuration			OPTIONAL,
	iE-Extensions					ProtocolExtensionContainer { { RequestedDLPRSResourceSet-Item-ExtIEs} } OPTIONAL,
	...
}

RequestedDLPRSResourceSet-Item-ExtIEs NRPPA-PROTOCOL-EXTENSION ::= {
	...
}

RequestedDLPRSResource-List::= SEQUENCE (SIZE (1..maxnoofPRSresource)) OF RequestedDLPRSResource-Item

RequestedDLPRSResource-Item  ::= SEQUENCE {
	qCLInfo					PRSResource-QCLInfo		OPTIONAL,
	iE-Extensions			ProtocolExtensionContainer { { RequestedDLPRSResource-Item-ExtIEs} } OPTIONAL,
	...
}

RequestedDLPRSResource-Item-ExtIEs NRPPA-PROTOCOL-EXTENSION ::= {
	...
}


RequestedSRSTransmissionCharacteristics ::= SEQUENCE {
	numberOfTransmissions	INTEGER (0..500,...)							OPTIONAL,
-- The IE shall be present if the Resource Type IE is set to the value “periodic” --
	resourceType			ENUMERATED {periodic, semi-persistent, aperiodic, ...},
	bandwidth				BandwidthSRS,
	listOfSRSResourceSet	SEQUENCE (SIZE (1.. maxnoSRS-ResourceSets)) OF SRSResourceSet-Item	OPTIONAL,
	sSBInformation			SSBInfo		OPTIONAL,
	iE-Extensions			ProtocolExtensionContainer { { RequestedSRSTransmissionCharacteristics-ExtIEs} } OPTIONAL,
	...
}

RequestedSRSTransmissionCharacteristics-ExtIEs NRPPA-PROTOCOL-EXTENSION ::= {
	{ ID id-SrsFrequency								CRITICALITY ignore EXTENSION SrsFrequency											PRESENCE optional }|
	{ ID id-Bandwidth-Aggregation-Request-Indication 	CRITICALITY ignore EXTENSION Bandwidth-Aggregation-Request-Indication	PRESENCE optional }|
	{ ID id-PosValidityAreaCellList 					CRITICALITY ignore EXTENSION PosValidityAreaCellList							PRESENCE optional }|
	{ ID id-ValidityAreaSpecificSRSInformation			CRITICALITY ignore EXTENSION ValidityAreaSpecificSRSInformation			PRESENCE optional }|
	{ ID id-ValidityAreaSpecificSRSInformationExtended	CRITICALITY ignore EXTENSION ValidityAreaSpecificSRSInformationExtended	PRESENCE optional },
	...
}


ResourceMapping ::= SEQUENCE {
	startPosition			INTEGER (0..13),
	nrofSumbols				ENUMERATED {n1, n2, n4, n8, n12},
	iE-Extensions		ProtocolExtensionContainer { { ResourceMapping-ExtIEs} }	OPTIONAL,
	...
}

ResourceMapping-ExtIEs NRPPA-PROTOCOL-EXTENSION ::= {
	...
}


RequestedSRSPreconfigurationCharacteristics-List  ::= SEQUENCE (SIZE (1..maxnoPreconfiguredSRS)) OF RequestedSRSPreconfigurationCharacteristics-Item

RequestedSRSPreconfigurationCharacteristics-Item ::= SEQUENCE {
	requestedSRSTransmissionCharacteristics 	RequestedSRSTransmissionCharacteristics,
	iE-Extensions			ProtocolExtensionContainer {{ RequestedSRSPreconfigurationCharacteristics-Item-ExtIEs}}			OPTIONAL,
	...
}

RequestedSRSPreconfigurationCharacteristics-Item-ExtIEs NRPPA-PROTOCOL-EXTENSION ::= {
	...
}


SRSResourceSet-Item ::= SEQUENCE { 
	numberOfSRSResourcePerSet		INTEGER (1..16, ...)			OPTIONAL,
	periodicityList					PeriodicityList					OPTIONAL,
	spatialRelationInformation		SpatialRelationInfo		OPTIONAL,
	pathlossReferenceInformation	PathlossReferenceInformation	OPTIONAL,
	iE-Extensions			ProtocolExtensionContainer { { SRSResourceSet-Item-ExtIEs} } OPTIONAL,
	...
}

SRSResourceSet-Item-ExtIEs NRPPA-PROTOCOL-EXTENSION ::= {
	{ ID id-SRSSpatialRelationPerSRSResource	CRITICALITY ignore	EXTENSION SpatialRelationPerSRSResource PRESENCE optional},
	...
}

RequestType ::= ENUMERATED {activate, deactivate, ...}

ResourceSetType  ::= CHOICE {
	periodic			ResourceSetTypePeriodic,
	semi-persistent		ResourceSetTypeSemi-persistent,
	aperiodic			ResourceSetTypeAperiodic,
	choice-extension				ProtocolIE-Single-Container {{ ResourceSetType-ExtIEs }}
}

ResourceSetType-ExtIEs NRPPA-PROTOCOL-IES ::= {
	...
}

ResourceSetTypePeriodic ::= SEQUENCE {
periodicSet			ENUMERATED{true, ...},
	iE-Extensions		ProtocolExtensionContainer { { ResourceSetTypePeriodic-ExtIEs} }	OPTIONAL,
	...
}

ResourceSetTypePeriodic-ExtIEs NRPPA-PROTOCOL-EXTENSION ::= {
	...
}

ResourceSetTypeSemi-persistent ::= SEQUENCE {
semi-persistentSet	ENUMERATED{true, ...},
	iE-Extensions		ProtocolExtensionContainer { { ResourceSetTypeSemi-persistent-ExtIEs} }	OPTIONAL,
	...
}

ResourceSetTypeSemi-persistent-ExtIEs NRPPA-PROTOCOL-EXTENSION ::= {
	...
}

ResourceSetTypeAperiodic ::= SEQUENCE {
	sRSResourceTrigger		 	INTEGER(1..3),
	slotoffset					INTEGER(0..32),
	iE-Extensions				ProtocolExtensionContainer { { ResourceSetTypeAperiodic-ExtIEs} }	OPTIONAL,
	...
}

ResourceSetTypeAperiodic-ExtIEs NRPPA-PROTOCOL-EXTENSION ::= {
	...
}


ResourceType ::= CHOICE {
	periodic						ResourceTypePeriodic,
	semi-persistent					ResourceTypeSemi-persistent,
	aperiodic						ResourceTypeAperiodic,
	choice-extension				ProtocolIE-Single-Container {{ ResourceType-ExtIEs }}
}

ResourceType-ExtIEs NRPPA-PROTOCOL-IES ::= {
	...
}
 
ResourceTypePeriodic ::= SEQUENCE {
	periodicity		 		  ENUMERATED{slot1, slot2, slot4, slot5, slot8, slot10, slot16, slot20, slot32, slot40, slot64, slot80, slot160, slot320, slot640, slot1280, slot2560, ...},
	offset					INTEGER(0..2559, ...),
	iE-Extensions			ProtocolExtensionContainer { { ResourceTypePeriodic-ExtIEs} }	OPTIONAL,
	...
}

ResourceTypePeriodic-ExtIEs NRPPA-PROTOCOL-EXTENSION ::= {
	...
}

ResourceTypeSemi-persistent ::= SEQUENCE {
	periodicity			ENUMERATED{slot1, slot2, slot4, slot5, slot8, slot10, slot16, slot20, slot32, slot40, slot64, slot80, slot160, slot320, slot640, slot1280, slot2560, ...},
	offset				INTEGER(0..2559, ...),
	iE-Extensions		ProtocolExtensionContainer { { ResourceTypeSemi-persistent-ExtIEs} }	OPTIONAL,
	...
}

ResourceTypeSemi-persistent-ExtIEs NRPPA-PROTOCOL-EXTENSION ::= {
	...
}

ResourceTypeAperiodic ::= SEQUENCE {
aperiodicResourceType	   ENUMERATED{true, ...},
	iE-Extensions		ProtocolExtensionContainer { { ResourceTypeAperiodic-ExtIEs} }	OPTIONAL,
	...
}

ResourceTypeAperiodic-ExtIEs NRPPA-PROTOCOL-EXTENSION ::= {
	...
}


ResourceTypePos ::= CHOICE {
	periodic			ResourceTypePeriodicPos,
	semi-persistent		ResourceTypeSemi-persistentPos,
	aperiodic			ResourceTypeAperiodicPos,
	choice-extension				ProtocolIE-Single-Container {{ ResourceTypePos-ExtIEs }}
}

ResourceTypePos-ExtIEs NRPPA-PROTOCOL-IES ::= {
	...
}

ResourceTypePeriodicPos ::= SEQUENCE {
sRSPeriodicity		   SRSPeriodicity,
offset				INTEGER(0..81919, ...),
	iE-Extensions		ProtocolExtensionContainer { { ResourceTypePeriodicPos-ExtIEs} }	OPTIONAL,
	...
}

ResourceTypePeriodicPos-ExtIEs NRPPA-PROTOCOL-EXTENSION ::= {
		{ ID id-SRSPosPeriodicConfigHyperSFNIndex		CRITICALITY ignore	EXTENSION SRSPosPeriodicConfigHyperSFNIndex	PRESENCE optional },
	...
}

ResourceTypeSemi-persistentPos ::= SEQUENCE {
sRSPeriodicity		   SRSPeriodicity,
offset				INTEGER(0..81919, ...),
	iE-Extensions		ProtocolExtensionContainer { { ResourceTypeSemi-persistentPos-ExtIEs} }	OPTIONAL,
	...
}

ResourceTypeSemi-persistentPos-ExtIEs NRPPA-PROTOCOL-EXTENSION ::= {
		{ ID id-SRSPosPeriodicConfigHyperSFNIndex		CRITICALITY ignore	EXTENSION SRSPosPeriodicConfigHyperSFNIndex	PRESENCE optional },
	...
}

ResourceTypeAperiodicPos ::= SEQUENCE {
slotOffset          INTEGER (0..32),
	iE-Extensions		ProtocolExtensionContainer { { ResourceTypeAperiodicPos-ExtIEs} }	OPTIONAL,
	...
}

ResourceTypeAperiodicPos-ExtIEs NRPPA-PROTOCOL-EXTENSION ::= {
	...
}

ResponseTime ::= SEQUENCE {
	time          INTEGER (1..128,...),
	timeUnit	  ENUMERATED {second, ten-seconds, ten-milliseconds,...},
	iE-Extensions		ProtocolExtensionContainer { { ResponseTime-ExtIEs} }	OPTIONAL,
	...
}

ResponseTime-ExtIEs NRPPA-PROTOCOL-EXTENSION ::= {
	...
}


ResultCSI-RSRP ::= SEQUENCE (SIZE (1.. maxCellReportNR)) OF ResultCSI-RSRP-Item

ResultCSI-RSRP-Item ::= SEQUENCE {
	nR-PCI					NR-PCI,
	nR-ARFCN				NR-ARFCN,
	cGI-NR				CGI-NR													OPTIONAL,
	valueCSI-RSRP-Cell		ValueRSRP-NR												OPTIONAL,
	cSI-RSRP-PerCSI-RS		ResultCSI-RSRP-PerCSI-RS									OPTIONAL,
	iE-Extensions		ProtocolExtensionContainer { { ResultCSI-RSRP-Item-ExtIEs} }	OPTIONAL,
	...
}

ResultCSI-RSRP-Item-ExtIEs NRPPA-PROTOCOL-EXTENSION ::= {
	...
}

ResultCSI-RSRP-PerCSI-RS ::= SEQUENCE (SIZE (1.. maxIndexesReport)) OF ResultCSI-RSRP-PerCSI-RS-Item

ResultCSI-RSRP-PerCSI-RS-Item ::= SEQUENCE {
	cSI-RS-Index		INTEGER (0..95),
	valueCSI-RSRP		ValueRSRP-NR,
	iE-Extensions		ProtocolExtensionContainer { { ResultCSI-RSRP-PerCSI-RS-Item-ExtIEs} }	OPTIONAL,
	...
}

ResultCSI-RSRP-PerCSI-RS-Item-ExtIEs NRPPA-PROTOCOL-EXTENSION ::= {
	...
}

ResultCSI-RSRQ ::= SEQUENCE (SIZE (1.. maxCellReportNR)) OF ResultCSI-RSRQ-Item

ResultCSI-RSRQ-Item ::= SEQUENCE {
	nR-PCI				NR-PCI,
	nR-ARFCN			NR-ARFCN,
	cGI-NR			CGI-NR														OPTIONAL,
	valueCSI-RSRQ-Cell	ValueRSRQ-NR													OPTIONAL,
	cSI-RSRQ-PerCSI-RS		ResultCSI-RSRQ-PerCSI-RS									OPTIONAL,
	iE-Extensions		ProtocolExtensionContainer { { ResultCSI-RSRQ-Item-ExtIEs} }	OPTIONAL,
	...
}

ResultCSI-RSRQ-Item-ExtIEs NRPPA-PROTOCOL-EXTENSION ::= {
	...
}

ResultCSI-RSRQ-PerCSI-RS ::= SEQUENCE (SIZE (1.. maxIndexesReport)) OF ResultCSI-RSRQ-PerCSI-RS-Item

ResultCSI-RSRQ-PerCSI-RS-Item ::= SEQUENCE {
	cSI-RS-Index		INTEGER (0..95),
	valueCSI-RSRQ		ValueRSRQ-NR,
	iE-Extensions		ProtocolExtensionContainer { { ResultCSI-RSRQ-PerCSI-RS-Item-ExtIEs} }	OPTIONAL,
	...
}

ResultCSI-RSRQ-PerCSI-RS-Item-ExtIEs NRPPA-PROTOCOL-EXTENSION ::= {
	...
}

ResultEUTRA ::= SEQUENCE (SIZE (1.. maxEUTRAMeas)) OF ResultEUTRA-Item

ResultEUTRA-Item ::= SEQUENCE {
	pCI-EUTRA			PCI-EUTRA,
	eARFCN				EARFCN,
	valueRSRP-EUTRA		ValueRSRP-EUTRA												OPTIONAL,
	valueRSRQ-EUTRA		ValueRSRQ-EUTRA												OPTIONAL,
	cGI-EUTRA			CGI-EUTRA													OPTIONAL,
	iE-Extensions		ProtocolExtensionContainer { { ResultEUTRA-Item-ExtIEs} }	OPTIONAL,
	...
}

ResultEUTRA-Item-ExtIEs NRPPA-PROTOCOL-EXTENSION ::= {
	...
}


ResultRSRP-EUTRA ::= SEQUENCE (SIZE (1.. maxCellReport)) OF ResultRSRP-EUTRA-Item

ResultRSRP-EUTRA-Item ::= SEQUENCE {
	pCI-EUTRA			PCI-EUTRA,
	eARFCN				EARFCN,
	cGI-EUTRA			CGI-EUTRA OPTIONAL,
	valueRSRP-EUTRA		ValueRSRP-EUTRA,
	iE-Extensions		ProtocolExtensionContainer { { ResultRSRP-EUTRA-Item-ExtIEs} } OPTIONAL,
	...
}

ResultRSRP-EUTRA-Item-ExtIEs NRPPA-PROTOCOL-EXTENSION ::= {
	...
}

ResultRSRQ-EUTRA ::= SEQUENCE (SIZE (1.. maxCellReport)) OF ResultRSRQ-EUTRA-Item

ResultRSRQ-EUTRA-Item ::= SEQUENCE {
	pCI-EUTRA			PCI-EUTRA,
	eARFCN				EARFCN,
	cGI-UTRA			CGI-EUTRA OPTIONAL,
	valueRSRQ-EUTRA		ValueRSRQ-EUTRA,
	iE-Extensions		ProtocolExtensionContainer { { ResultRSRQ-EUTRA-Item-ExtIEs} } OPTIONAL,
	...
}

ResultRSRQ-EUTRA-Item-ExtIEs NRPPA-PROTOCOL-EXTENSION ::= {
	...
}


ResultSS-RSRP ::= SEQUENCE (SIZE (1.. maxCellReportNR)) OF ResultSS-RSRP-Item

ResultSS-RSRP-Item ::= SEQUENCE {
	nR-PCI				NR-PCI,
	nR-ARFCN			NR-ARFCN,
	cGI-NR			CGI-NR													OPTIONAL,
	valueSS-RSRP-Cell	ValueRSRP-NR												OPTIONAL,
	sS-RSRP-PerSSB		ResultSS-RSRP-PerSSB										OPTIONAL,
	iE-Extensions		ProtocolExtensionContainer { { ResultSS-RSRP-Item-ExtIEs} }	OPTIONAL,
	...
}

ResultSS-RSRP-Item-ExtIEs NRPPA-PROTOCOL-EXTENSION ::= {
	...
}

ResultSS-RSRP-PerSSB ::= SEQUENCE (SIZE (1.. maxIndexesReport)) OF ResultSS-RSRP-PerSSB-Item

ResultSS-RSRP-PerSSB-Item ::= SEQUENCE {
	sSB-Index			SSB-Index,
	valueSS-RSRP		ValueRSRP-NR,
	iE-Extensions		ProtocolExtensionContainer { { ResultSS-RSRP-PerSSB-Item-ExtIEs} }	OPTIONAL,
	...
}

ResultSS-RSRP-PerSSB-Item-ExtIEs NRPPA-PROTOCOL-EXTENSION ::= {
	...
}

ResultSS-RSRQ ::= SEQUENCE (SIZE (1.. maxCellReportNR)) OF ResultSS-RSRQ-Item

ResultSS-RSRQ-Item ::= SEQUENCE {
	nR-PCI				NR-PCI,
	nR-ARFCN			NR-ARFCN,
	cGI-NR			CGI-NR													OPTIONAL,
	valueSS-RSRQ-Cell	ValueRSRQ-NR												OPTIONAL,
	sS-RSRQ-PerSSB		ResultSS-RSRQ-PerSSB										OPTIONAL,
	iE-Extensions		ProtocolExtensionContainer { { ResultSS-RSRQ-Item-ExtIEs} }	OPTIONAL,
	...
}

ResultSS-RSRQ-Item-ExtIEs NRPPA-PROTOCOL-EXTENSION ::= {
	...
}

ResultSS-RSRQ-PerSSB ::= SEQUENCE (SIZE (1.. maxIndexesReport)) OF ResultSS-RSRQ-PerSSB-Item

ResultSS-RSRQ-PerSSB-Item ::= SEQUENCE {
	sSB-Index			SSB-Index,
	valueSS-RSRQ		ValueRSRQ-NR,
	iE-Extensions		ProtocolExtensionContainer { { ResultSS-RSRQ-PerSSB-Item-ExtIEs} }	OPTIONAL,
	...
}

ResultSS-RSRQ-PerSSB-Item-ExtIEs NRPPA-PROTOCOL-EXTENSION ::= {
	...
}


ResultGERAN ::= SEQUENCE (SIZE (1.. maxGERANMeas)) OF ResultGERAN-Item

ResultGERAN-Item ::= SEQUENCE {
	bCCH				BCCH,
	physCellIDGERAN		PhysCellIDGERAN,
	rSSI				RSSI,
	iE-Extensions		ProtocolExtensionContainer { { ResultGERAN-Item-ExtIEs} } OPTIONAL,
	...
}

ResultGERAN-Item-ExtIEs NRPPA-PROTOCOL-EXTENSION ::= {
	...
}


ResultNR ::= SEQUENCE (SIZE (1.. maxNRMeas)) OF ResultNR-Item

ResultNR-Item ::= SEQUENCE {
	nR-PCI				NR-PCI,
	nR-ARFCN			NR-ARFCN,
	valueSS-RSRP-Cell	ValueRSRP-NR											OPTIONAL,
	valueSS-RSRQ-Cell	ValueRSRQ-NR											OPTIONAL,
	sS-RSRP-PerSSB		ResultSS-RSRP-PerSSB									OPTIONAL,
	sS-RSRQ-PerSSB		ResultSS-RSRQ-PerSSB									OPTIONAL,
	cGI-NR				CGI-NR													OPTIONAL,
	iE-Extensions		ProtocolExtensionContainer { { ResultNR-Item-ExtIEs} }	OPTIONAL,
	...
}

ResultNR-Item-ExtIEs NRPPA-PROTOCOL-EXTENSION ::= {
	...
}


ResultUTRAN ::= SEQUENCE (SIZE (1.. maxUTRANMeas)) OF ResultUTRAN-Item

ResultUTRAN-Item ::= SEQUENCE {
	uARFCN				UARFCN,
	physCellIDUTRAN		CHOICE {
		physCellIDUTRA-FDD		PhysCellIDUTRA-FDD,
		physCellIDUTRA-TDD		PhysCellIDUTRA-TDD
	},
	uTRA-RSCP			UTRA-RSCP OPTIONAL,
	uTRA-EcN0			UTRA-EcN0 OPTIONAL,
	iE-Extensions		ProtocolExtensionContainer { { ResultUTRAN-Item-ExtIEs} } OPTIONAL,
	...
}

ResultUTRAN-Item-ExtIEs NRPPA-PROTOCOL-EXTENSION ::= {
	...
}

RSSI ::= INTEGER (0..63, ...)

RxTxTimingErrorMargin ::= ENUMERATED {tc0dot5, tc1, tc2, tc4, tc8, tc12, tc16, tc20, tc24, tc32, tc40, tc48, tc64, tc80, tc96, tc128, ...}

-- S

SCS-480	::= INTEGER(0..319)

SCS-960	::= INTEGER(0..639)

SCS-SpecificCarrier ::= SEQUENCE {
    offsetToCarrier                     INTEGER (0..2199,...),
    subcarrierSpacing                   ENUMERATED {kHz15, kHz30, kHz60, kHz120,..., kHz480, kHz960},
    carrierBandwidth                    INTEGER (1..275,...),
iE-Extensions					ProtocolExtensionContainer { { SCS-SpecificCarrier-ExtIEs } } OPTIONAL,
	...
}

SCS-SpecificCarrier-ExtIEs NRPPA-PROTOCOL-EXTENSION ::= {
	...
} 


Search-window-information ::= SEQUENCE {
	expectedPropagationDelay		INTEGER (-3841..3841,...),
	delayUncertainty				INTEGER (1..246,...),
	iE-Extensions					ProtocolExtensionContainer { { Search-window-information-ExtIEs } } OPTIONAL,
	...
}

Search-window-information-ExtIEs NRPPA-PROTOCOL-EXTENSION ::= {
	...
}


RelativeTime1900 ::= BIT STRING (SIZE (64))


SFNInitialisationTime-EUTRA ::= BIT STRING (SIZE (64))

SlotNumber ::= INTEGER (0..79)

SlotOffsetForRemainingHopsList ::= SEQUENCE (SIZE (1..maxnoofHopsMinusOne)) OF SlotOffsetForRemainingHopsItem

SlotOffsetForRemainingHopsItem ::= SEQUENCE {
	slotOffsetRemainingHops			SlotOffsetRemainingHops,
	iE-Extensions					ProtocolExtensionContainer { { SlotOffsetForRemainingHopsItem-ExtIEs} } OPTIONAL,
	...
}

SlotOffsetForRemainingHopsItem-ExtIEs NRPPA-PROTOCOL-EXTENSION ::= {
	...
}

SlotOffsetRemainingHops ::= CHOICE {
	aperiodic			SlotOffsetRemainingHopsAperiodic,
	semi-persistent		SlotOffsetRemainingHopsSemiPersistent,
	periodic			SlotOffsetRemainingHopsPeriodic,
	choice-extension		ProtocolIE-Single-Container {{ SlotOffsetRemainingHops-ExtIEs }}
}

SlotOffsetRemainingHops-ExtIEs NRPPA-PROTOCOL-IES ::= {
	...
}

SlotOffsetRemainingHopsAperiodic ::= SEQUENCE {
	slotOffset			INTEGER (1..32)			OPTIONAL,
	startPosition		INTEGER (0..13)			OPTIONAL,
	iE-Extensions		ProtocolExtensionContainer { { SlotOffsetRemainingHopsAperiodic-ExtIEs} }	OPTIONAL,
	...
}

SlotOffsetRemainingHopsAperiodic-ExtIEs NRPPA-PROTOCOL-EXTENSION ::= {
	...
}

SlotOffsetRemainingHopsSemiPersistent ::= SEQUENCE {
	sRSperiodicity		SRSPeriodicity,
	offset				INTEGER(0..81919, ...),
	startPosition		INTEGER (0..13) 			OPTIONAL,
	iE-Extensions		ProtocolExtensionContainer { { SlotOffsetRemainingHopsSemiPersistent-ExtIEs} }	OPTIONAL,
	...
}

SlotOffsetRemainingHopsSemiPersistent-ExtIEs NRPPA-PROTOCOL-EXTENSION ::= {
	...
}

SlotOffsetRemainingHopsPeriodic ::= SEQUENCE {
	sRSperiodicity		SRSPeriodicity,
	offset				INTEGER(0..81919, ...),
	startPosition		INTEGER (0..13) 			OPTIONAL,
	iE-Extensions		ProtocolExtensionContainer { { SlotOffsetRemainingHopsSemiPeriodic-ExtIEs} }	OPTIONAL,
	...
}

SlotOffsetRemainingHopsSemiPeriodic-ExtIEs NRPPA-PROTOCOL-EXTENSION ::= {
	...
}


SpatialDirectionInformation ::= SEQUENCE {
	nR-PRS-Beam-Information			NR-PRS-Beam-Information,
	iE-Extensions					ProtocolExtensionContainer { { SpatialDirectionInformation-ExtIEs } } OPTIONAL,
	...
}

SpatialDirectionInformation-ExtIEs NRPPA-PROTOCOL-EXTENSION ::= {
	...
} 


SpatialRelationInfo ::= SEQUENCE {
	spatialRelationforResourceID					SpatialRelationforResourceID,
	iE-Extensions		ProtocolExtensionContainer { {SpatialRelationInfo-ExtIEs} }	OPTIONAL,
	...
}

SpatialRelationInfo-ExtIEs NRPPA-PROTOCOL-EXTENSION ::= {
	...
}


SpatialRelationforResourceID ::= SEQUENCE (SIZE(1..maxnoSpatialRelations)) OF SpatialRelationforResourceIDItem

SpatialRelationforResourceIDItem ::= SEQUENCE {
	referenceSignal		ReferenceSignal,
	iE-Extensions		ProtocolExtensionContainer { {SpatialRelationforResourceIDItem-ExtIEs} }	OPTIONAL,
	...
}

SpatialRelationforResourceIDItem-ExtIEs NRPPA-PROTOCOL-EXTENSION ::= {
	...
}


SpatialRelationPerSRSResource ::= SEQUENCE {
	spatialRelationPerSRSResource-List	SpatialRelationPerSRSResource-List,
	iE-Extensions		ProtocolExtensionContainer { { SpatialRelationPerSRSResource-ExtIEs} }	OPTIONAL,
	...
}

SpatialRelationPerSRSResource-ExtIEs NRPPA-PROTOCOL-EXTENSION ::= {
	...
}

SpatialRelationPerSRSResource-List::= SEQUENCE(SIZE (1.. maxnoSRS-ResourcePerSet)) OF SpatialRelationPerSRSResourceItem

SpatialRelationPerSRSResourceItem ::= SEQUENCE {
	referenceSignal		ReferenceSignal,
	iE-Extensions		ProtocolExtensionContainer { {SpatialRelationPerSRSResourceItem-ExtIEs} }	OPTIONAL,
	...
}

SpatialRelationPerSRSResourceItem-ExtIEs NRPPA-PROTOCOL-EXTENSION ::= {
	...
}

SpatialRelationPos ::= CHOICE {
	sSBPos					SSB,
	pRSInformationPos		PRSInformationPos,
	choice-extension				ProtocolIE-Single-Container {{ SpatialInformationPos-ExtIEs }}
}

SpatialInformationPos-ExtIEs NRPPA-PROTOCOL-IES ::= {
	...
}
 


SRSConfig  ::= SEQUENCE {
	sRSResource-List			SRSResource-List OPTIONAL,
	posSRSResource-List			PosSRSResource-List OPTIONAL,
	sRSResourceSet-List			SRSResourceSet-List OPTIONAL,
	posSRSResourceSet-List		PosSRSResourceSet-List OPTIONAL,
	iE-Extensions					ProtocolExtensionContainer { { SRSConfig-ExtIEs } } OPTIONAL,
	...
}

SRSConfig-ExtIEs NRPPA-PROTOCOL-EXTENSION ::= {
	...
}

SRSCarrier-List ::= SEQUENCE (SIZE(1.. maxnoSRS-Carriers)) OF SRSCarrier-List-Item

SRSCarrier-List-Item ::= SEQUENCE {
	pointA							INTEGER (0..3279165),
	uplinkChannelBW-PerSCS-List		UplinkChannelBW-PerSCS-List,
	activeULBWP						ActiveULBWP,
	pCI-NR							INTEGER (0..1007)		OPTIONAL,
iE-Extensions					ProtocolExtensionContainer { { SRSCarrier-List-Item-ExtIEs } } OPTIONAL,
	...
}

SRSCarrier-List-Item-ExtIEs NRPPA-PROTOCOL-EXTENSION ::= {
	...
}


SRSConfiguration ::= SEQUENCE {
	sRSCarrier-List		SRSCarrier-List,
	iE-Extensions			ProtocolExtensionContainer { { SRSConfiguration-ExtIEs } } OPTIONAL,
	...
}

SRSConfiguration-ExtIEs NRPPA-PROTOCOL-EXTENSION ::= {
{ ID id-PosSRSResourceSet-Aggregation-List	CRITICALITY ignore EXTENSION PosSRSResourceSet-Aggregation-List		PRESENCE optional },
	...
} 

SrsFrequency ::= INTEGER (0..3279165)

SRSPortIndex ::= ENUMERATED{id1000, id1001, id1002, id1003, ...}

SRSPosPeriodicConfigHyperSFNIndex ::=ENUMERATED {even0, odd1}

SRSPosResourceID ::= INTEGER (0..63)

SRSResource::= SEQUENCE {
	sRSResourceID					SRSResourceID,
	nrofSRS-Ports					ENUMERATED {port1, ports2, ports4},
	transmissionComb				TransmissionComb,
	startPosition					INTEGER (0..13),
	nrofSymbols						ENUMERATED {n1, n2, n4},
	repetitionFactor				ENUMERATED {n1, n2, n4},
	freqDomainPosition				INTEGER (0..67),
	freqDomainShift					INTEGER (0..268),
	c-SRS							INTEGER (0..63),
	b-SRS							INTEGER (0..3),
	b-hop							INTEGER (0..3),
	groupOrSequenceHopping			ENUMERATED { neither, groupHopping, sequenceHopping },
	resourceType					ResourceType,
	sequenceId						INTEGER (0..1023),
	iE-Extensions					ProtocolExtensionContainer { { SRSResource-ExtIEs } } OPTIONAL,
	...
}

SRSResource-ExtIEs NRPPA-PROTOCOL-EXTENSION ::= {
	{ ID id-nrofSymbolsExtended			CRITICALITY ignore EXTENSION NrofSymbolsExtended 			PRESENCE optional}|
	{ ID id-repetitionFactorExtended		CRITICALITY ignore EXTENSION RepetitionFactorExtended 	PRESENCE optional}|
	{ ID id-StartRBHopping			CRITICALITY ignore EXTENSION StartRBHopping 			PRESENCE optional}|
	{ ID id-StartRBIndex			CRITICALITY ignore EXTENSION StartRBIndex 			PRESENCE optional},

	...
}

SRSResourceID ::= INTEGER (0..63)

SRSResource-List ::= SEQUENCE (SIZE (1..maxnoSRS-Resources)) OF SRSResource

SRSResourceSet-List ::= SEQUENCE (SIZE (1..maxnoSRS-ResourceSets)) OF SRSResourceSet 

SRSResourceID-List::= SEQUENCE (SIZE (1..maxnoSRS-ResourcePerSet)) OF SRSResourceID

SRSResourceSet::= SEQUENCE {
	sRSResourceSetID1                INTEGER(0..15),
	sRSResourceID-List				SRSResourceID-List,
	resourceSetType					ResourceSetType,
	iE-Extensions					ProtocolExtensionContainer { { SRSResourceSet-ExtIEs } } OPTIONAL,
	...
}

SRSResourceSet-ExtIEs NRPPA-PROTOCOL-EXTENSION ::= {
	...
}

SRSResourceSetID ::= INTEGER (0..15, ...)

SRSResourceTrigger ::= SEQUENCE {
	aperiodicSRSResourceTriggerList					AperiodicSRSResourceTriggerList,
	iE-Extensions		ProtocolExtensionContainer { {SRSResourceTrigger-ExtIEs} }	OPTIONAL,
	...
}

SRSResourceTrigger-ExtIEs NRPPA-PROTOCOL-EXTENSION ::= {
	...
}

SRSResourcetype ::= SEQUENCE {
	sRSResourceTypeChoice					SRSResourceTypeChoice,
	iE-Extensions		ProtocolExtensionContainer { { SRSResourcetype-ExtIEs} }	OPTIONAL,
	...
}

SRSResourcetype-ExtIEs NRPPA-PROTOCOL-EXTENSION ::= {
	{ ID id-SRSPortIndex	CRITICALITY ignore EXTENSION SRSPortIndex	PRESENCE optional},
	...
}

SRSResourceTypeChoice ::= CHOICE {
	sRSResourceInfo			SRSInfo,
	posSRSResourceInfo		PosSRSInfo,
	...
}

SRSInfo ::= SEQUENCE {
	sRSResource			SRSResourceID,
	...
}

SRSTransmissionStatus ::= ENUMERATED {stopped,...,area-specific-SRS-activated}

PosSRSInfo ::= SEQUENCE {
	posSRSResourceID		SRSPosResourceID,
	...
}


SSBInfo ::= SEQUENCE {
	listOfSSBInfo		SEQUENCE (SIZE (1..maxNoSSBs)) OF SSBInfoItem,
	iE-Extensions		ProtocolExtensionContainer { {SSBInfo-ExtIEs} }	OPTIONAL,
	...
}

SSBInfo-ExtIEs NRPPA-PROTOCOL-EXTENSION ::= {
	...
}



SSBInfoItem ::= SEQUENCE {
	sSB-Configuration	TF-Configuration,
	pCI-NR				INTEGER  (0..1007),
	iE-Extensions		ProtocolExtensionContainer { { SSBInfoItem-ExtIEs} }	OPTIONAL,
	...
}


SSBInfoItem-ExtIEs NRPPA-PROTOCOL-EXTENSION ::= {
	...
}


SSB ::= SEQUENCE {
	pCI-NR				INTEGER  (0..1007),
	ssb-index			SSB-Index	OPTIONAL,
	iE-Extensions		ProtocolExtensionContainer { {SSB-ExtIEs} }	OPTIONAL,
	...
}

SSB-ExtIEs NRPPA-PROTOCOL-EXTENSION ::= {
	...
}


SSBBurstPosition ::= CHOICE {
	shortBitmap			BIT STRING (SIZE(4)),
	mediumBitmap		BIT STRING (SIZE(8)),
	longBitmap			BIT STRING (SIZE(64)),
	choice-extension		ProtocolIE-Single-Container { { SSBBurstPosition-ExtIEs} }
}

SSBBurstPosition-ExtIEs NRPPA-PROTOCOL-IES ::= {
	...
}

SSB-Index ::= INTEGER(0..63)


SSID ::= OCTET STRING (SIZE(1..32))


StartRBIndex  ::= CHOICE{
	freqScalingFactor2  INTEGER(0..1),
	freqScalingFactor4  INTEGER(0..3),
	choice-extension	ProtocolIE-Single-Container { { StartRBIndex-ExtIEs} }
}

StartRBIndex-ExtIEs NRPPA-PROTOCOL-IES ::= {
	...
}

StartRBHopping  ::= ENUMERATED {enable}


StartTimeAndDuration ::= SEQUENCE {
	startTime			RelativeTime1900				OPTIONAL,
	duration			INTEGER (0..90060, ...)			OPTIONAL,
	iE-Extensions		ProtocolExtensionContainer { { StartTimeAndDuration-ExtIEs} }	OPTIONAL,
	...
}

StartTimeAndDuration-ExtIEs NRPPA-PROTOCOL-EXTENSION ::= {
	...
}


SymbolIndex ::= INTEGER (0..13)

SystemFrameNumber ::= INTEGER (0..1023)

SystemInformation ::= SEQUENCE (SIZE (1.. maxNrOfPosSImessage)) OF SEQUENCE {
	broadcastPeriodicity				BroadcastPeriodicity,
	posSIBs								PosSIBs,
	iE-Extensions						ProtocolExtensionContainer { { SystemInformation-ExtIEs} }	OPTIONAL,
	...
}

SystemInformation-ExtIEs NRPPA-PROTOCOL-EXTENSION ::= {
	...
}

SRSReservationType::= ENUMERATED {reserve, release, ...}


SRSPreconfiguration-List  ::= SEQUENCE (SIZE (1.. maxnoPreconfiguredSRS)) OF SRSPreconfiguration-Item

SRSPreconfiguration-Item ::= SEQUENCE {
	sRSConfiguration		SRSConfiguration,
	posValidityAreaCellList PosValidityAreaCellList,
	iE-Extensions			ProtocolExtensionContainer {{ SRSPreconfiguration-Item-ExtIEs}}			OPTIONAL,
	...
}

SRSPreconfiguration-Item-ExtIEs NRPPA-PROTOCOL-EXTENSION ::= {
	...
}

SRSPeriodicity ::= ENUMERATED {slot1, slot2, slot4, slot5, slot8, slot10, slot16, slot20, slot32, slot40, slot64, slot80, slot160, slot320, slot640, slot1280, slot2560, slot5120, slot10240, slot40960, slot81920, ..., slot128, slot256, slot512, slot20480}


-- T

TAC ::= OCTET STRING (SIZE(3))

TDD-Config-EUTRA-Item ::= SEQUENCE {
	subframeAssignment			ENUMERATED { sa0, sa1, sa2, sa3, sa4, sa5, sa6, ... },
	iE-Extensions				ProtocolExtensionContainer { { TDD-Config-EUTRA-Item-Item-ExtIEs } } OPTIONAL,
	...
}

TDD-Config-EUTRA-Item-Item-ExtIEs NRPPA-PROTOCOL-EXTENSION ::= {
	...
}

TRPTEGInformation ::= CHOICE {
	rxTx-TEG			RxTxTEG,
	rx-TEG				RxTEG,
	choice-extension		ProtocolIE-Single-Container { { TRPTEGInformation-ExtIEs} }
}

TRPTEGInformation-ExtIEs NRPPA-PROTOCOL-IES ::= {
	...
}

RxTxTEG ::= SEQUENCE {
	tRP-RxTx-TEGInformation			TRP-RxTx-TEGInformation,
	tRP-Tx-TEGInformation			TRP-Tx-TEGInformation		OPTIONAL,
	iE-extensions		ProtocolExtensionContainer { { RxTxTEG-ExtIEs } }	OPTIONAL,
	...
}

RxTxTEG-ExtIEs NRPPA-PROTOCOL-EXTENSION ::= {
	...
}

RxTEG ::= SEQUENCE {
	tRP-Rx-TEGInformation		TRP-Rx-TEGInformation,
	tRP-Tx-TEGInformation		TRP-Tx-TEGInformation,
	iE-extensions      ProtocolExtensionContainer { { RxTEG-ExtIEs } }	OPTIONAL,
	...
}

RxTEG-ExtIEs NRPPA-PROTOCOL-EXTENSION ::= {
	...
}

TimingErrorMargin ::= ENUMERATED {tc0, tc2, tc4, tc6, tc8, tc12, tc16, tc20, tc24, tc32, tc40, tc48, tc56, tc64, tc72, tc80, ...}

TF-Configuration ::= SEQUENCE {
	sSB-frequency				INTEGER (0..3279165),
	sSB-subcarrier-spacing		ENUMERATED {kHz15, kHz30, kHz120, kHz240, ..., kHz60, kHz480, kHz960},
	-- The value kHz60 is not supported in this version of the specification.
	sSB-Transmit-power			INTEGER (-60..50),
	sSB-periodicity				ENUMERATED {ms5, ms10, ms20, ms40, ms80, ms160, ...},
	sSB-half-frame-offset		INTEGER(0..1),
	sSB-SFN-offset				INTEGER(0..15),
	sSB-BurstPosition			SSBBurstPosition	OPTIONAL,
	sFN-initialisation-time		RelativeTime1900	 OPTIONAL,
	iE-Extensions		ProtocolExtensionContainer { { TF-Configuration-ExtIEs} }	OPTIONAL,
	...
}

TF-Configuration-ExtIEs NRPPA-PROTOCOL-EXTENSION ::= {
	...
}


TimeStamp ::= SEQUENCE {
	systemFrameNumber		SystemFrameNumber,
	slotIndex				TimeStampSlotIndex,
	measurementTime			RelativeTime1900	OPTIONAL,
	iE-Extension			ProtocolExtensionContainer { { TimeStamp-ExtIEs} }	OPTIONAL,
	...
}

TimeStamp-ExtIEs NRPPA-PROTOCOL-EXTENSION ::= {
	{ ID id-SymbolIndex	 CRITICALITY ignore		EXTENSION SymbolIndex  	PRESENCE optional }, 
	...
}

TimeStampSlotIndex ::= CHOICE {
	sCS-15			INTEGER(0..9),
	sCS-30			INTEGER(0..19),
	sCS-60			INTEGER(0..39),
	sCS-120			INTEGER(0..79),
	choice-extension		ProtocolIE-Single-Container { { TimeStampSlotIndex-ExtIEs} }
}

TimeStampSlotIndex-ExtIEs NRPPA-PROTOCOL-IES ::= {
	{ ID id-SCS-480		CRITICALITY reject	TYPE SCS-480 PRESENCE mandatory}|
	{ ID id-SCS-960		CRITICALITY reject	TYPE SCS-960 PRESENCE mandatory},

	...
}

TimeWindowDurationMeasurement ::= CHOICE {
	durationSlots		ENUMERATED {n1, n2, n4, n6, n8, n12, n16, ...},
	choice-extension		ProtocolIE-Single-Container { { TimeWindowDurationMeasurement-ExtIEs} }
}

TimeWindowDurationMeasurement-ExtIEs NRPPA-PROTOCOL-IES ::= {
	...
}

TimeWindowDurationSRS ::= CHOICE {
	durationSymbols		ENUMERATED {n1, n2, n4, n8, n12, ...},
	durationSlots		ENUMERATED {n1, n2, n4, n6, n8, n12, n16, ...},
	choice-extension		ProtocolIE-Single-Container { { TimeWindowDurationSRS-ExtIEs} }
}

TimeWindowDurationSRS-ExtIEs NRPPA-PROTOCOL-IES ::= {
	...
}

TimeWindowPeriodicityMeasurement ::= ENUMERATED {ms160, ms320, ms640, ms1280, ms2560, ms5120, ms10240, ms20480, ms40960, ms61440, ms81920, ms368640, ms737280, ms1843200, ...}

TimeWindowPeriodicitySRS ::= ENUMERATED {ms0dot125, ms0dot25, ms0dot5, ms0dot625, ms1, ms1dot25, ms2, ms2dot5, ms4, ms5, ms8, ms10, ms16, ms20, ms32, ms40, ms64, ms80, ms160, ms320, ms640, ms1280, ms2560, ms5120, ms10240, ...}

TimeWindowStartSRS ::= SEQUENCE {
	systemFrameNumber		SystemFrameNumber,
	slotNumber				SlotNumber,
	symbolIndex				INTEGER (0..13),
	iE-Extension			ProtocolExtensionContainer { { TimeWindowStartSRS-ExtIEs} }	OPTIONAL,
	...
}

TimeWindowStartSRS-ExtIEs NRPPA-PROTOCOL-EXTENSION ::= {
	...
}


TimingReportingGranularityFactorExtended ::=INTEGER(-6..-1, ...)

TimeWindowInformation-Measurement-List ::= SEQUENCE (SIZE (1.. maxnoofTimeWindowMeas)) OF TimeWindowInformation-Measurement-Item

TimeWindowInformation-Measurement-Item ::= SEQUENCE {
	timeWindowDurationMeasurement		TimeWindowDurationMeasurement,
	timeWindowType						ENUMERATED {single, periodic, ...},
	timeWindowPeriodicityMeasurement	TimeWindowPeriodicityMeasurement		OPTIONAL,
-- This IE shall be present if the Time Window Type IE is set to the value “periodic”. --
	timeWindowStart						TimeWindowStart,
	iE-Extension			ProtocolExtensionContainer { { TimeWindowInformation-Measurement-Item-ExtIEs} }	OPTIONAL,
	...
}

TimeWindowInformation-Measurement-Item-ExtIEs NRPPA-PROTOCOL-EXTENSION ::= {
	...
}

TimeWindowInformation-SRS-List ::= SEQUENCE (SIZE (1.. maxnoofTimeWindowSRS)) OF TimeWindowInformation-SRS-Item

TimeWindowInformation-SRS-Item ::= SEQUENCE {
	timeWindowStartSRS					TimeWindowStartSRS,
	timeWindowDurationSRS				TimeWindowDurationSRS,
	timeWindowType						ENUMERATED {single, periodic, ...},
	timeWindowPeriodicitySRS			TimeWindowPeriodicitySRS				OPTIONAL,
-- This IE shall be present if the Time Window Type IE is set to the value “periodic”. --
	iE-Extension			ProtocolExtensionContainer { { TimeWindowInformation-SRS-Item-ExtIEs} }	OPTIONAL,
	...
}

TimeWindowInformation-SRS-Item-ExtIEs NRPPA-PROTOCOL-EXTENSION ::= {
	...
}

TimeWindowStart ::= SEQUENCE {
	systemFrameNumber		SystemFrameNumber,
	slotNumber				SlotNumber,
	symbolIndex				INTEGER (0..13),
	iE-Extension			ProtocolExtensionContainer { { TimeWindowStart-ExtIEs} }	OPTIONAL,
	...
}

TimeWindowStart-ExtIEs NRPPA-PROTOCOL-EXTENSION ::= {
	...
}


TP-ID-EUTRA ::= INTEGER (0..4095, ...)

TP-Type-EUTRA ::= ENUMERATED { prs-only-tp, ... }


TransmissionComb ::= CHOICE {
	n2    SEQUENCE {
            combOffset-n2              INTEGER (0..1),
            cyclicShift-n2             INTEGER (0..7)
        },
    n4    SEQUENCE {
            combOffset-n4              INTEGER (0..3),
            cyclicShift-n4             INTEGER (0..11)
        },
	choice-extension				ProtocolIE-Single-Container { { TransmissionComb-ExtIEs} }
}
TransmissionComb-ExtIEs NRPPA-PROTOCOL-IES ::= {
{ ID id-transmissionCombn8	CRITICALITY reject TYPE TransmissionCombn8 PRESENCE mandatory},
	...
}

TransmissionCombn8 ::= SEQUENCE {
            combOffset-n8              INTEGER (0..7),
            cyclicShift-n8             INTEGER (0..5),
	iE-Extensions					ProtocolExtensionContainer { { TransmissionCombn8-ExtIEs } } OPTIONAL
}

TransmissionCombn8-ExtIEs NRPPA-PROTOCOL-EXTENSION ::= {
	...
}


TransmissionCombPos ::= CHOICE {
	n2    SEQUENCE {
            combOffset-n2              INTEGER (0..1),
            cyclicShift-n2             INTEGER (0..7)
        },
    n4    SEQUENCE {
            combOffset-n4              INTEGER (0..3),
            cyclicShift-n4             INTEGER (0..11)
        },
    n8    SEQUENCE {
            combOffset-n8              INTEGER (0..7),
            cyclicShift-n8             INTEGER (0..5)
        },

	choice-extension				ProtocolIE-Single-Container { { TransmissionCombPos-ExtIEs} }
}
TransmissionCombPos-ExtIEs NRPPA-PROTOCOL-IES ::= {
	...
}

TRPBeamAntennaInformation ::= SEQUENCE {
	choice-TRP-Beam-Antenna-Info-Item		Choice-TRP-Beam-Antenna-Info-Item,
	iE-Extensions			ProtocolExtensionContainer {{ TRPBeamAntennaInformation-ExtIEs}}				OPTIONAL,
	...
}

TRPBeamAntennaInformation-ExtIEs NRPPA-PROTOCOL-EXTENSION ::= {
	...
}

Choice-TRP-Beam-Antenna-Info-Item ::= CHOICE {
	reference					TRP-ID,
	explicit					TRP-BeamAntennaExplicitInformation,
	noChange					NULL,
	choice-extension				ProtocolIE-Single-Container { { Choice-TRP-Beam-Info-Item-ExtIEs } }
}

Choice-TRP-Beam-Info-Item-ExtIEs NRPPA-PROTOCOL-IES ::= {
	...
}

TRP-BeamAntennaExplicitInformation ::= SEQUENCE {
	trp-BeamAntennaAngles					TRP-BeamAntennaAngles,
	lcs-to-gcs-translation	 				LCS-to-GCS-Translation										OPTIONAL,
	iE-Extensions			ProtocolExtensionContainer {{ TRP-BeamAntennaExplicitInformation-ExtIEs}}				OPTIONAL,
	...
}

TRP-BeamAntennaExplicitInformation-ExtIEs NRPPA-PROTOCOL-EXTENSION ::= {
	...
}

TRP-BeamAntennaAngles ::= SEQUENCE (SIZE (1.. maxnoAzimuthAngles)) OF TRP-BeamAntennaAnglesList-Item

TRP-BeamAntennaAnglesList-Item ::= SEQUENCE {
	trp-azimuth-angle					INTEGER (0..359),
	trp-azimuth-angle-fine				INTEGER (0..9)	OPTIONAL,
	trp-elevation-angle-list			SEQUENCE (SIZE (1.. maxnoElevationAngles)) OF TRP-ElevationAngleList-Item,
	iE-Extensions			ProtocolExtensionContainer {{ TRP-BeamAntennaAnglesList-Item-ExtIEs}}			OPTIONAL,
	...
}

TRP-BeamAntennaAnglesList-Item-ExtIEs NRPPA-PROTOCOL-EXTENSION ::= {
	...
}

TRP-ElevationAngleList-Item ::= SEQUENCE {
	trp-elevation-angle					INTEGER (0..180),
	trp-elevation-angle-fine			INTEGER (0..9)	OPTIONAL,
	trp-beam-power-list					SEQUENCE (SIZE (2..maxNumResourcesPerAngle)) OF TRP-Beam-Power-Item,
	iE-Extensions			ProtocolExtensionContainer {{ TRP-ElevationAngleList-Item-ExtIEs}}			OPTIONAL,
	...
}

TRP-ElevationAngleList-Item-ExtIEs NRPPA-PROTOCOL-EXTENSION ::= {
	...
}

TRP-Beam-Power-Item ::= SEQUENCE {
	pRSResourceSetID				PRS-Resource-Set-ID		OPTIONAL,
	pRSResourceID					PRS-Resource-ID,
	relativePower				INTEGER (0..30), --negative value
	relativePowerFine				INTEGER (0..9)			OPTIONAL, --negative value
	iE-Extensions			ProtocolExtensionContainer {{ TRP-Beam-Power-Item-ExtIEs}}					OPTIONAL,
	...
}

TRP-Beam-Power-Item-ExtIEs NRPPA-PROTOCOL-EXTENSION ::= {
	...
}

TRPMeasurementQuantities ::= SEQUENCE (SIZE (1..maxnoPosMeas)) OF TRPMeasurementQuantitiesList-Item

TRPMeasurementQuantitiesList-Item ::= SEQUENCE {
	tRPMeasurementType					TRPMeasurementType,
	timingReportingGranularityFactor	INTEGER (0..5) OPTIONAL,
	iE-Extensions			ProtocolExtensionContainer {{ TRPMeasurementQuantitiesList-Item-ExtIEs}}		OPTIONAL,
	...
}

TRPMeasurementQuantitiesList-Item-ExtIEs NRPPA-PROTOCOL-EXTENSION ::= {
	{ID id-TimingReportingGranularityFactorExtended	CRITICALITY ignore EXTENSION TimingReportingGranularityFactorExtended PRESENCE optional}|
	{ID id-ChannelResponseInformation				CRITICALITY ignore EXTENSION ChannelResponseInformation 				PRESENCE optional},
	...
}

TRPMeasurementType ::= ENUMERATED {
	gNB-RxTxTimeDiff, 
	uL-SRS-RSRP, 
	uL-AoA, 
	uL-RTOA, 
	...,
	multiple-UL-AoA,
	uL-SRS-RSRPP,
	ul-RSCP,
	ul-SRS-TDCT
}

TrpMeasurementResult ::= SEQUENCE (SIZE (1.. maxnoPosMeas)) OF TrpMeasurementResultItem
TrpMeasurementResultItem ::= SEQUENCE {
	measuredResultsValue				TrpMeasuredResultsValue,
	timeStamp							TimeStamp,
	measurementQuality					TrpMeasurementQuality						OPTIONAL,
	measurementBeamInfo					MeasurementBeamInfo				OPTIONAL,
	iE-Extensions		ProtocolExtensionContainer {{TrpMeasurementResultItem-ExtIEs}}		OPTIONAL,
	...
}

TrpMeasurementResultItem-ExtIEs NRPPA-PROTOCOL-EXTENSION ::= {
	{ ID id-SRSResourcetype	CRITICALITY ignore EXTENSION SRSResourcetype PRESENCE optional}|
	{ ID id-ARP-ID		CRITICALITY ignore EXTENSION ARP-ID 	PRESENCE optional}|
	{ ID id-LoS-NLoSInformation		CRITICALITY ignore EXTENSION LoS-NLoSInformation		PRESENCE optional }|
	{ ID id-Mobile-TRP-LocationInformation	CRITICALITY ignore EXTENSION Mobile-TRP-LocationInformation	PRESENCE optional }|
	{ ID id-MeasuredFrequencyHops			CRITICALITY ignore EXTENSION MeasuredFrequencyHops					PRESENCE optional }|
	{ ID id-AggregatedPosSRSResourceID-List	CRITICALITY ignore EXTENSION AggregatedPosSRSResourceID-List	PRESENCE optional }|
	{ ID id-MeasBasedOnAggregatedResources			CRITICALITY ignore EXTENSION MeasBasedOnAggregatedResources PRESENCE optional }|
	{ ID id-Inferred-measurement			CRITICALITY ignore EXTENSION Inferred-measurement PRESENCE optional },
	...
}

TrpMeasuredResultsValue ::= CHOICE {
	uL-AngleOfArrival	UL-AoA,
	uL-SRS-RSRP			UL-SRS-RSRP,
	uL-RTOA				UL-RTOAMeasurement,
	gNB-RxTxTimeDiff	GNB-RxTxTimeDiff,
	choice-extension							ProtocolIE-Single-Container { { TrpMeasuredResultsValue-ExtIEs } }
}

TrpMeasuredResultsValue-ExtIEs NRPPA-PROTOCOL-IES ::= {
	{ ID id-ZoA		CRITICALITY reject TYPE ZoA PRESENCE mandatory}|
	{ ID id-MultipleULAoA	CRITICALITY reject TYPE MultipleULAoA PRESENCE mandatory}|
			{ ID id-UL-SRS-RSRPP	CRITICALITY reject TYPE UL-SRS-RSRPP 	PRESENCE mandatory}|
	{ ID id-UL-RSCPMeas		CRITICALITY reject TYPE UL-RSCPMeas	PRESENCE mandatory}|
	{ ID id-UL-SRS-TDCT		CRITICALITY reject TYPE UL-SRS-TDCT	PRESENCE mandatory},
	...
}

TrpMeasurementQuality ::= CHOICE {
	timingMeasQuality		TrpMeasurementTimingQuality,
	angleMeasQuality		TrpMeasurementAngleQuality,
	choice-Extension		ProtocolIE-Single-Container {{ TrpMeasurementQuality-ExtIEs}}

}

TrpMeasurementQuality-ExtIEs NRPPA-PROTOCOL-IES ::= {
	{ID id-TRPPhaseQuality 	CRITICALITY ignore TYPE TRPPhaseQuality PRESENCE mandatory },
	...
}

TrpMeasurementTimingQuality ::= SEQUENCE {
	measurementQuality		INTEGER (0..31),
	resolution				ENUMERATED {m0dot1, m1, m10, m30, ...},
	iE-extensions			ProtocolExtensionContainer { { TrpMeasurementTimingQuality-ExtIEs } } OPTIONAL,
	...
}

TrpMeasurementTimingQuality-ExtIEs NRPPA-PROTOCOL-EXTENSION ::= {
	...
}

TrpMeasurementAngleQuality ::= SEQUENCE {
	azimuthQuality		INTEGER (0..255),
	zenithQuality		INTEGER (0..255)	OPTIONAL,
	resolution			ENUMERATED {deg0dot1, ...},
	iE-extensions		ProtocolExtensionContainer { { TrpMeasurementAngleQuality-ExtIEs } } OPTIONAL,
	...
}

TrpMeasurementAngleQuality-ExtIEs NRPPA-PROTOCOL-EXTENSION ::= {
	...
}

TRPPhaseQuality ::= SEQUENCE {
	phaseQualityIndex	INTEGER(0..179),
	resolution			ENUMERATED {deg0dot1, deg1, ...},
	iE-extensions		ProtocolExtensionContainer { { TRPPhaseQuality-ExtIEs } } OPTIONAL,
	...
}

TRPPhaseQuality-ExtIEs NRPPA-PROTOCOL-EXTENSION ::= {
	...
}

TRP-MeasurementRequestList ::= SEQUENCE (SIZE (1..maxNoOfMeasTRPs)) OF TRP-MeasurementRequestItem

TRP-MeasurementRequestItem ::= SEQUENCE {
	tRP-ID							TRP-ID, 
	search-window-information		Search-window-information	OPTIONAL, 
	iE-extensions					ProtocolExtensionContainer { { TRP-MeasurementRequestItem-ExtIEs } } OPTIONAL,
	...
}

TRP-MeasurementRequestItem-ExtIEs NRPPA-PROTOCOL-EXTENSION ::= {
	{ ID id-Cell-ID		CRITICALITY ignore EXTENSION CGI-NR		PRESENCE optional }|
	{ ID id-AoA-SearchWindow		CRITICALITY ignore EXTENSION AoA-AssistanceInfo		PRESENCE optional }|
	{ ID id-NumberOfTRPRxTEG		CRITICALITY ignore EXTENSION NumberOfTRPRxTEG		PRESENCE optional }|
	{ ID id-NumberOfTRPRxTxTEG		CRITICALITY ignore EXTENSION NumberOfTRPRxTxTEG		PRESENCE optional },
	...
}

TRP-MeasurementResponseList ::= SEQUENCE (SIZE (1..maxNoOfMeasTRPs)) OF TRP-MeasurementResponseItem

TRP-MeasurementResponseItem ::= SEQUENCE {
	tRP-ID							TRP-ID, 
	measurementResult				TrpMeasurementResult,
	iE-extensions					ProtocolExtensionContainer { { TRP-MeasurementResponseItem-ExtIEs } } OPTIONAL,
	...
}

TRP-MeasurementResponseItem-ExtIEs NRPPA-PROTOCOL-EXTENSION ::= {
	{ ID id-Cell-ID								CRITICALITY ignore 	EXTENSION 				CGI-NR								PRESENCE optional }|
	{ ID id-PositioningDataCollectionNeeded		CRITICALITY ignore	EXTENSION  PositioningDataCollectionNeeded		PRESENCE optional},
	...
}


TRP-MeasurementUpdateList ::= SEQUENCE (SIZE (1..maxNoOfMeasTRPs)) OF TRP-MeasurementUpdateItem

TRP-MeasurementUpdateItem ::= SEQUENCE {
	tRP-ID						TRP-ID, 
	aoA-window-information		AoA-AssistanceInfo	OPTIONAL, 
	iE-extensions					ProtocolExtensionContainer { { TRP-MeasurementUpdateItem-ExtIEs } } OPTIONAL,
	...
}

TRP-MeasurementUpdateItem-ExtIEs NRPPA-PROTOCOL-EXTENSION ::= {
	{ ID id-NumberOfTRPRxTEG		CRITICALITY ignore EXTENSION NumberOfTRPRxTEG		PRESENCE optional }|
	{ ID id-NumberOfTRPRxTxTEG		CRITICALITY ignore EXTENSION NumberOfTRPRxTxTEG		PRESENCE optional },
	...
}


TRPInformationListTRPResp ::= SEQUENCE (SIZE (1.. maxnoTRPs)) OF SEQUENCE {
	tRPInformation					TRPInformation,
	iE-Extensions					ProtocolExtensionContainer { {TRPInformationTRPResp-ExtIEs} } OPTIONAL,
	...
}

TRPInformationTRPResp-ExtIEs NRPPA-PROTOCOL-EXTENSION ::= {
	...
}

TRPInformation ::= SEQUENCE {
	tRP-ID							TRP-ID,
	tRPInformationTypeResponseList	TRPInformationTypeResponseList,
	iE-Extensions					ProtocolExtensionContainer { { TRPInformation-ExtIEs } }		OPTIONAL,
	...
}

TRPInformation-ExtIEs NRPPA-PROTOCOL-EXTENSION ::= {
	{ ID id-Mobile-IAB-MT-UE-ID			CRITICALITY reject EXTENSION Mobile-IAB-MT-UE-ID		PRESENCE optional}|
--This IE shall be present if the TRP type IE is set to the value "mobile trp"
	{ ID id-WAB-MT-UE-ID			CRITICALITY reject EXTENSION WAB-MT-UE-ID		PRESENCE optional},
--This IE shall be present if the TRP type IE is set to the value "mobile trp of wab-gnb"
	...
}

TRPInformationTypeResponseList ::= SEQUENCE (SIZE (1..maxnoTRPInfoTypes)) OF TRPInformationTypeResponseItem

TRPInformationTypeResponseItem ::= CHOICE {
	pCI-NR										INTEGER  (0..1007),
	cGI-NR									CGI-NR,
	aRFCN										INTEGER (0..3279165), 
	pRSConfiguration							PRSConfiguration,
	sSBinformation								SSBInfo,
	sFNInitialisationTime						RelativeTime1900,
	spatialDirectionInformation					SpatialDirectionInformation,
	geographicalCoordinates						GeographicalCoordinates,
	choice-extension							ProtocolIE-Single-Container { { TRPInformationTypeResponseItem-ExtIEs } }
}

TRPInformationTypeResponseItem-ExtIEs NRPPA-PROTOCOL-IES ::= {
	{ ID id-TRPType						CRITICALITY reject TYPE TRPType						PRESENCE mandatory }|
	{ ID id-OnDemandPRS				CRITICALITY reject TYPE OnDemandPRS-Info				PRESENCE mandatory}|
	{ ID id-TRPTxTEGAssociation		CRITICALITY reject TYPE TRPTxTEGAssociation			PRESENCE mandatory}|
	{ ID id-TRPBeamAntennaInformation	CRITICALITY reject TYPE TRPBeamAntennaInformation		PRESENCE mandatory }|
	{ ID id-Mobile-TRP-LocationInformation	CRITICALITY ignore TYPE Mobile-TRP-LocationInformation	PRESENCE mandatory }|
	{ ID id-CommonTAParameters			CRITICALITY reject TYPE CommonTAParameters			PRESENCE mandatory },
	...

}

	
	TRPInformationTypeListTRPReq ::= SEQUENCE (SIZE(1.. maxnoTRPInfoTypes)) OF ProtocolIE-Single-Container { {TRPInformationTypeItemTRPReq} }
	
TRPInformationTypeItemTRPReq NRPPA-PROTOCOL-IES ::= {
	{ ID id-TRPInformationTypeItem	 CRITICALITY reject		TYPE TRPInformationTypeItem  	PRESENCE mandatory },
	...
}

TRPInformationTypeItem ::= ENUMERATED {
		nrPCI,
		nG-RAN-CGI,
		arfcn, 
		pRSConfig,
		sSBInfo,
		sFNInitTime,
		spatialDirectInfo,
		geoCoord,

		...,
		trp-type,
		ondemandPRSInfo,
		trpTxTeg,
		beam-antenna-info,
		mobile-trp-location-info,
		commonTA
}
	
	TRPList ::= SEQUENCE (SIZE(1.. maxnoTRPs)) OF TRPItem
	
TRPItem ::= SEQUENCE {
	tRP-ID		TRP-ID,
	iE-Extensions	ProtocolExtensionContainer { {TRPItem-ExtIEs} } OPTIONAL,
		...
}

TRPItem-ExtIEs NRPPA-PROTOCOL-EXTENSION ::= {
		...
	}

TRP-ID ::= INTEGER (1.. maxnoTRPs, ...)


TRPPositionDefinitionType ::= CHOICE {
	direct		TRPPositionDirect,
	referenced	TRPPositionReferenced,
	choice-extension							ProtocolIE-Single-Container { { TRPPositionDefinitionType-ExtIEs } }
}

TRPPositionDefinitionType-ExtIEs NRPPA-PROTOCOL-IES ::= {
	...
}


TRPPositionDirect ::= SEQUENCE {
	accuracy	TRPPositionDirectAccuracy,
	iE-extensions		ProtocolExtensionContainer { { TRPPositionDirect-ExtIEs } }	OPTIONAL,
	...
}

TRPPositionDirect-ExtIEs NRPPA-PROTOCOL-EXTENSION ::= {
	...
}

TRPPositionDirectAccuracy ::= CHOICE {
	tRPPosition			NG-RANAccessPointPosition						,
	tRPHAposition		NGRANHighAccuracyAccessPointPosition	,
	choice-extension			ProtocolIE-Single-Container { { TRPPositionDirectAccuracy-ExtIEs } }
}

TRPPositionDirectAccuracy-ExtIEs NRPPA-PROTOCOL-IES ::= {
	...
}


TRPPositionReferenced ::= SEQUENCE {
	referencePoint					ReferencePoint,
	referencePointType				TRPReferencePointType,
	iE-extensions							ProtocolExtensionContainer { { TRPPositionReferenced-ExtIEs } }	OPTIONAL,
	...
}

TRPPositionReferenced-ExtIEs NRPPA-PROTOCOL-EXTENSION ::= {
	...
}

TRP-PRS-Information-List ::= SEQUENCE (SIZE(1.. maxnoPRSTRPs)) OF TRP-PRS-Information-List-Item

TRP-PRS-Information-List-Item ::= SEQUENCE {
		tRP-ID				TRP-ID,
		nR-PCI				NR-PCI,
		cGI-NR				CGI-NR					OPTIONAL,
		pRSConfiguration							PRSConfiguration,
		iE-Extensions	ProtocolExtensionContainer { { TRP-PRS-Information-List-Item-ExtIEs} } OPTIONAL,
		...
}

TRP-PRS-Information-List-Item-ExtIEs NRPPA-PROTOCOL-EXTENSION ::= {
	...
}

TRPReferencePointType ::= CHOICE {
	tRPPositionRelativeGeodetic			RelativeGeodeticLocation,
	tRPPositionRelativeCartesian		RelativeCartesianLocation,
	choice-extension							ProtocolIE-Single-Container { { TRPReferencePointType-ExtIEs } }
}

TRPReferencePointType-ExtIEs NRPPA-PROTOCOL-IES ::= {
	...
}

TRP-Rx-TEGInformation ::= SEQUENCE {
	tRP-Rx-TEGID					INTEGER (0..31),
	tRP-Rx-TimingErrorMargin		TimingErrorMargin,
	iE-Extensions		ProtocolExtensionContainer { { TRP-Rx-TEGInformation-ExtIEs } } OPTIONAL,
	...
}

TRP-Rx-TEGInformation-ExtIEs NRPPA-PROTOCOL-EXTENSION ::= {
	...
}

TRP-RxTx-TEGInformation ::= SEQUENCE {
	tRP-RxTx-TEGID					INTEGER (0..255),
	tRP-RxTx-TimingErrorMargin		RxTxTimingErrorMargin,
	iE-Extensions		ProtocolExtensionContainer { { TRP-RxTx-TEGInformation-ExtIEs } } OPTIONAL,
	...
}

TRP-RxTx-TEGInformation-ExtIEs NRPPA-PROTOCOL-EXTENSION ::= {
	...
}

TRP-Tx-TEGInformation ::= SEQUENCE {
	tRP-Tx-TEGID					INTEGER (0..7),
	tRP-Tx-TimingErrorMargin		TimingErrorMargin,
	iE-Extensions		ProtocolExtensionContainer { { TRP-Tx-TEGInformation-ExtIEs } } OPTIONAL,
	...
}

TRP-Tx-TEGInformation-ExtIEs NRPPA-PROTOCOL-EXTENSION ::= {
	...
}

TRPTxTEGAssociation ::= SEQUENCE (SIZE(1.. maxnoTRPTEGs)) OF TRPTEGItem

TRPTEGItem ::= SEQUENCE {
		tRP-Tx-TEGInformation	TRP-Tx-TEGInformation,
		dl-PRSResourceSetID		PRS-Resource-Set-ID,
		dl-PRSResourceID-List	SEQUENCE (SIZE(1.. maxPRS-ResourcesPerSet)) OF DLPRSResourceID-Item	OPTIONAL,
	iE-Extensions					ProtocolExtensionContainer { { TRPTEGItem-ExtIEs } } OPTIONAL,
	...
}

TRPTEGItem-ExtIEs NRPPA-PROTOCOL-EXTENSION ::= {
	...
}

DLPRSResourceID-Item ::= SEQUENCE {
	dl-PRSResourceID		PRS-Resource-ID,
	iE-Extensions			ProtocolExtensionContainer { { DLPRSResource-Item-ExtIEs} }	OPTIONAL,
	...
}

DLPRSResource-Item-ExtIEs NRPPA-PROTOCOL-EXTENSION ::= {
	...
}


TRPType ::= ENUMERATED {
	prsOnlyTP,
	srsOnlyRP,
	tp,
	rp,
	trp,
	...,
	mobile-trp,
	mobile-trp-of-wab-gnb
}


TypeOfError ::= ENUMERATED {
	not-understood,
	missing,
	...
}

TxHoppingConfiguration ::= SEQUENCE {
	overlapValue						ENUMERATED {rb0, rb1, rb2, rb4},
	numberOfHops						INTEGER (2..6),
	slotOffsetForRemainingHopsList		SlotOffsetForRemainingHopsList,
	iE-extensions		ProtocolExtensionContainer { { TxHoppingConfiguration-ExtIEs } }	OPTIONAL,
	...
}

TxHoppingConfiguration-ExtIEs NRPPA-PROTOCOL-EXTENSION ::= {
	...
}



-- U

UARFCN ::= INTEGER (0..16383, ...)

UE-Measurement-ID ::= INTEGER (1..15, ..., 16..256)

UEReportingInformation::= SEQUENCE {
	reportingAmount				ENUMERATED {ma0, ma1, ma2, ma4, ma8, ma16, ma32, ma64},
	reportingInterval			ENUMERATED {none, one, two, four, eight, ten, sixteen, twenty, thirty-two, sixty-four, ...},
	iE-extensions			ProtocolExtensionContainer { { UEReportingInformation-ExtIEs } }	OPTIONAL,
	...
}

UEReportingInformation-ExtIEs NRPPA-PROTOCOL-EXTENSION ::= {
	{ ID id-UEReportingInterval-milliseconds			CRITICALITY ignore EXTENSION UEReportingInterval-milliseconds	PRESENCE optional },
	...
}

UEReportingInterval-milliseconds ::= INTEGER (1..999)

UE-Rx-Tx-Time-Diff ::= INTEGER (0..61565)

UE-TEG-ReportingPeriodicity ::= ENUMERATED {
	ms160,
	ms320,
	ms1280,
	ms2560,
	ms61440,
	ms81920,
	ms368640,
	ms737280,
	...
}

UETxTEGAssociationList ::= SEQUENCE (SIZE(1.. maxnoUETEGs)) OF UETxTEGAssociationItem

UETxTEGAssociationItem ::= SEQUENCE {
		uE-Tx-TEG-ID				INTEGER (0..7),
		posSRSResourceID-List		PosSRSResourceID-List,
		timeStamp					TimeStamp,
		carrierFreq					CarrierFreq				OPTIONAL,
	iE-Extensions					ProtocolExtensionContainer { { UETxTEGAssociationItem-ExtIEs } } OPTIONAL,
	...
}

UETxTEGAssociationItem-ExtIEs NRPPA-PROTOCOL-EXTENSION ::= {
	{ ID id-UETxTimingErrorMargin			CRITICALITY ignore EXTENSION TimingErrorMargin 	PRESENCE optional },
	...
}

SRSResourceID-Item ::= SEQUENCE {
	sRSResourceID                   SRSResourceID,
	iE-Extensions			ProtocolExtensionContainer { { SRSResourceID-Item-ExtIEs} }	OPTIONAL,
	...
}

SRSResourceID-Item-ExtIEs NRPPA-PROTOCOL-EXTENSION ::= {
	...
}

UE-TEG-Info-Request ::= ENUMERATED {onDemand, periodic, stop, ...}

UTRA-EcN0 ::= INTEGER (0..49, ...)

UTRA-RSCP ::= INTEGER (-5..91, ...)


UL-AoA ::= SEQUENCE {
	azimuthAoA					INTEGER (0..3599),
	zenithAoA					INTEGER (0..1799)				OPTIONAL,
	lCS-to-GCS-Translation	LCS-to-GCS-Translation		OPTIONAL,
	iE-extensions			ProtocolExtensionContainer { { UL-AoA-ExtIEs } }	OPTIONAL,
	...
}

UL-AoA-ExtIEs NRPPA-PROTOCOL-EXTENSION ::= {
	...
}


UL-RTOAMeasurement ::= SEQUENCE {
		uLRTOAmeas			ULRTOAMeas,
		additionalPathList	AdditionalPathList	OPTIONAL, 
	iE-extensions			ProtocolExtensionContainer { { UL-RTOAMeasurement-ExtIEs } }	OPTIONAL,	...
}

UL-RTOAMeasurement-ExtIEs NRPPA-PROTOCOL-EXTENSION ::= {
	{ ID id-ExtendedAdditionalPathList	CRITICALITY ignore EXTENSION ExtendedAdditionalPathList	PRESENCE optional}|
	{ ID id-TRP-Rx-TEGInformation		CRITICALITY ignore EXTENSION TRP-Rx-TEGInformation		PRESENCE optional},
	...
}

UL-RSCPMeas ::= SEQUENCE {
	uLRSCP				INTEGER (0..3599),
	iE-extensions		ProtocolExtensionContainer { { UL-RSCPMeas-ExtIEs } }	OPTIONAL,
	...
}

UL-RSCPMeas-ExtIEs NRPPA-PROTOCOL-EXTENSION ::= {
	...
}


ULRTOAMeas::= CHOICE {
	k0		INTEGER (0.. 1970049),
	k1		INTEGER (0.. 985025),
	k2		INTEGER (0.. 492513),
	k3		INTEGER (0.. 246257),
	k4		INTEGER (0.. 123129),
	k5		INTEGER (0.. 61565),	
	choice-extension		ProtocolIE-Single-Container { { ULRTOAMeas-ExtIEs } }
}
ULRTOAMeas-ExtIEs NRPPA-PROTOCOL-IES ::= {
	{ID id-ReportingGranularitykminus1 	CRITICALITY ignore TYPE ReportingGranularitykminus1 PRESENCE mandatory}|
	{ID id-ReportingGranularitykminus2 	CRITICALITY ignore TYPE ReportingGranularitykminus2 PRESENCE mandatory}|
	{ID id-ReportingGranularitykminus3 	CRITICALITY ignore TYPE ReportingGranularitykminus3 PRESENCE mandatory}|
	{ID id-ReportingGranularitykminus4 	CRITICALITY ignore TYPE ReportingGranularitykminus4 PRESENCE mandatory}|
	{ID id-ReportingGranularitykminus5 	CRITICALITY ignore TYPE ReportingGranularitykminus5 PRESENCE mandatory}|
	{ID id-ReportingGranularitykminus6 	CRITICALITY ignore TYPE ReportingGranularitykminus6 PRESENCE mandatory},
	...
}

UL-SRS-RSRP ::= INTEGER (0..126)

UL-SRS-RSRPP ::= SEQUENCE {
	firstPathRSRPP				INTEGER (0..126),
	iE-extensions			ProtocolExtensionContainer { { UL-SRS-RSRPP-ExtIEs } }	OPTIONAL,
	...
}

UL-SRS-RSRPP-ExtIEs NRPPA-PROTOCOL-EXTENSION ::= {
	...
}

UL-SRS-TDCT ::= SEQUENCE {
	uL-SRS-TDCT-List			UL-SRS-TDCT-List,
	iE-Extensions				ProtocolExtensionContainer { { UL-SRS-TDCT-ExtIEs } }	OPTIONAL,
	...
}

UL-SRS-TDCT-ExtIEs 	NRPPA-PROTOCOL-EXTENSION ::= {
	...
}

UL-SRS-TDCT-List ::= SEQUENCE (SIZE(1..maxnoofChannelRes)) OF UL-SRS-TDCT-Item
 
UL-SRS-TDCT-Item ::= SEQUENCE {
	timingInformation	UL-SRS-TDCT-Information, 
	powerInformation	UL-SRS-TDCP-Item				OPTIONAL,
	iE-Extensions		ProtocolExtensionContainer { { UL-SRS-TDCT-Item-ExtIEs } }	OPTIONAL,
	...
}
 
UL-SRS-TDCT-Item-ExtIEs NRPPA-PROTOCOL-EXTENSION ::= {
	...
}

UL-SRS-TDCT-Information ::= CHOICE {
	k0					INTEGER (0..1970049),
	k1					INTEGER (0..985025),
	k2					INTEGER (0..492513),
	k3					INTEGER (0..246257),
	k4					INTEGER (0..123129),
	k5					INTEGER (0..61565),	 
	choice-Extension		ProtocolIE-Single-Container {{ UL-SRS-TDCT-Information-ExtIEs}}
}

UL-SRS-TDCT-Information-ExtIEs NRPPA-PROTOCOL-IES ::= {
	...
}

UL-SRS-TDCP-Item ::= INTEGER (0..126)


UplinkChannelBW-PerSCS-List ::= SEQUENCE (SIZE (1..maxnoSCSs)) OF SCS-SpecificCarrier


Uncertainty-range-AoA ::= INTEGER (0..3599)

Uncertainty-range-ZoA ::= INTEGER (0..1799)


-- V

ValueRSRP-EUTRA ::= INTEGER (0..97, ...)

ValueRSRQ-EUTRA ::= INTEGER (0..34, ...)

ValueRSRP-NR ::= INTEGER (0..127)

ValueRSRQ-NR ::= INTEGER (0..127)

ValidityAreaSpecificSRSInformation ::= SEQUENCE {
	transmissionCombPos				TransmissionCombPos 	OPTIONAL,
	resourceMapping 				ResourceMapping			OPTIONAL,
	freqDomainShift					INTEGER (0..268)		OPTIONAL,
	c-SRS							INTEGER (0..63)			OPTIONAL,
	resourceTypePos					ResourceTypePos			OPTIONAL,
	sequenceIDPos					INTEGER (0..65535)		OPTIONAL,
	iE-extensions		ProtocolExtensionContainer { { ValidityAreaSpecificSRSInformation-ExtIEs } }	OPTIONAL,
	...
}

ValidityAreaSpecificSRSInformation-ExtIEs NRPPA-PROTOCOL-EXTENSION ::= {
	...
}

ValidityAreaSpecificSRSInformationExtended ::= SEQUENCE {
	posSRSResource-List			PosSRSResource-List		OPTIONAL,
	posSRSResourceSet-List		PosSRSResourceSet-List	OPTIONAL,
	iE-extensions		ProtocolExtensionContainer { { ValidityAreaSpecificSRSInformationExtended-ExtIEs } }	OPTIONAL,
	...
}

ValidityAreaSpecificSRSInformationExtended-ExtIEs NRPPA-PROTOCOL-EXTENSION ::= {
	...
}


-- W

WLANMeasurementQuantities ::= SEQUENCE (SIZE (0.. maxNoMeas)) OF ProtocolIE-Single-Container { {WLANMeasurementQuantities-ItemIEs} }

WLANMeasurementQuantities-ItemIEs NRPPA-PROTOCOL-IES ::= {
	{ ID id-WLANMeasurementQuantities-Item	CRITICALITY reject	TYPE WLANMeasurementQuantities-Item PRESENCE mandatory}}

WLANMeasurementQuantities-Item ::= SEQUENCE {
	wLANMeasurementQuantitiesValue			WLANMeasurementQuantitiesValue,
	iE-Extensions							ProtocolExtensionContainer { { WLANMeasurementQuantitiesValue-ExtIEs} } OPTIONAL,
	...
}

WLANMeasurementQuantitiesValue-ExtIEs NRPPA-PROTOCOL-EXTENSION ::= {
	...
}

WLANMeasurementQuantitiesValue ::= ENUMERATED {
	wlan,
	...
}

WLANMeasurementResult ::= SEQUENCE (SIZE (1..maxNoMeas)) OF WLANMeasurementResult-Item

WLANMeasurementResult-Item ::= SEQUENCE {
	wLAN-RSSI			WLAN-RSSI,
	sSID				SSID					OPTIONAL,
	bSSID				BSSID					OPTIONAL,
	hESSID				HESSID					OPTIONAL,
	operatingClass		WLANOperatingClass		OPTIONAL,
	countryCode			WLANCountryCode			OPTIONAL,
	wLANChannelList		WLANChannelList			OPTIONAL,
	wLANBand			WLANBand				OPTIONAL,
	iE-Extensions		ProtocolExtensionContainer { { WLANMeasurementResult-Item-ExtIEs } }	OPTIONAL,
	...
}

WLANMeasurementResult-Item-ExtIEs	NRPPA-PROTOCOL-EXTENSION ::= {
	...
}

WLAN-RSSI ::= INTEGER (0..141, ...)

WLANBand ::= ENUMERATED {band2dot4, band5, ...}

WLANChannelList ::= SEQUENCE (SIZE (1..maxWLANchannels)) OF WLANChannel

WLANChannel ::= INTEGER (0..255)

WLANCountryCode ::= ENUMERATED {
	unitedStates,
	europe,
	japan,
	global,
	...
}

WLANOperatingClass ::= INTEGER (0..255)

WAB-MT-UE-ID ::= OCTET STRING

-- X

-- Y

-- Z

ZoA ::= SEQUENCE {
	zenithAoA					INTEGER (0..1799),
	lCS-to-GCS-Translation	LCS-to-GCS-Translation		OPTIONAL,
	iE-extensions			ProtocolExtensionContainer { { ZoA-ExtIEs } }	OPTIONAL,
	...
}

ZoA-ExtIEs NRPPA-PROTOCOL-EXTENSION ::= {
	...
}


END

-- **************************************************************
--
-- Common definitions
--
-- **************************************************************

NRPPA-CommonDataTypes {
itu-t (0) identified-organization (4) etsi (0) mobileDomain (0) 
ngran-access (22) modules (3) nrppa (4) version1 (1) nrppa-CommonDataTypes (3)}

DEFINITIONS AUTOMATIC TAGS ::= 

BEGIN

-- **************************************************************
--
-- Extension constants
--
-- **************************************************************

maxPrivateIEs 									INTEGER ::= 65535
maxProtocolExtensions 							INTEGER ::= 65535
maxProtocolIEs									INTEGER ::= 65535

-- **************************************************************
--
-- Common Data Types
--
-- **************************************************************

Criticality		::= ENUMERATED { reject, ignore, notify }

NRPPATransactionID		::= INTEGER (0..32767)


Presence		::= ENUMERATED { optional, conditional, mandatory }

PrivateIE-ID	::= CHOICE {
	local			INTEGER (0.. maxPrivateIEs),
	global			OBJECT IDENTIFIER
}

ProcedureCode		::= INTEGER (0..255)

ProtocolIE-ID		::= INTEGER (0..maxProtocolIEs)

TriggeringMessage	::= ENUMERATED { initiating-message, successful-outcome, unsuccessful-outcome}

END

-- **************************************************************
--
-- Constant definitions
--
-- **************************************************************

NRPPA-Constants {
itu-t (0) identified-organization (4) etsi (0) mobileDomain (0) 
ngran-access (22) modules (3) nrppa (4) version1 (1) nrppa-Constants (4) }

DEFINITIONS AUTOMATIC TAGS ::= 

BEGIN

IMPORTS

	ProcedureCode,
	ProtocolIE-ID
FROM NRPPA-CommonDataTypes;

-- **************************************************************
--
-- Elementary Procedures
--
-- **************************************************************

id-errorIndication												ProcedureCode ::= 0
id-privateMessage												ProcedureCode ::= 1
id-e-CIDMeasurementInitiation									ProcedureCode ::= 2
id-e-CIDMeasurementFailureIndication							ProcedureCode ::= 3
id-e-CIDMeasurementReport										ProcedureCode ::= 4
id-e-CIDMeasurementTermination									ProcedureCode ::= 5
id-oTDOAInformationExchange										ProcedureCode ::= 6
id-assistanceInformationControl									ProcedureCode ::= 7
id-assistanceInformationFeedback								ProcedureCode ::= 8
id-positioningInformationExchange								ProcedureCode ::= 9
id-positioningInformationUpdate									ProcedureCode ::= 10
id-Measurement													ProcedureCode ::= 11
id-MeasurementReport											ProcedureCode ::= 12
id-MeasurementUpdate											ProcedureCode ::= 13
id-MeasurementAbort												ProcedureCode ::= 14
id-MeasurementFailureIndication									ProcedureCode ::= 15
id-tRPInformationExchange										ProcedureCode ::= 16
id-positioningActivation										ProcedureCode ::= 17
id-positioningDeactivation										ProcedureCode ::= 18
id-pRSConfigurationExchange										ProcedureCode ::= 19
id-measurementPreconfiguration									ProcedureCode ::= 20
id-measurementActivation										ProcedureCode ::= 21
id-sRSInformationReservationNotification						ProcedureCode ::= 22
id-positioningDataCollectionReport								ProcedureCode ::= 23


-- **************************************************************
--
-- Lists
--
-- **************************************************************

maxNrOfErrors								INTEGER ::= 256
maxCellinRANnode							INTEGER ::= 3840
maxIndexesReport							INTEGER ::= 64
maxNoMeas									INTEGER ::= 64
maxCellReport								INTEGER ::= 9
maxCellReportNR								INTEGER ::= 9
maxnoOTDOAtypes								INTEGER ::= 63
maxServCell									INTEGER ::= 5
maxEUTRAMeas								INTEGER ::= 8
maxGERANMeas								INTEGER ::= 8
maxNRMeas									INTEGER ::= 8
maxUTRANMeas								INTEGER ::= 8
maxWLANchannels								INTEGER ::= 16
maxnoFreqHoppingBandsMinusOne				INTEGER ::= 7
maxNoPath									INTEGER ::= 2
	maxNrOfPosSImessage							INTEGER ::= 32
	maxnoAssistInfoFailureListItems				INTEGER ::= 32
	maxNrOfSegments								INTEGER ::= 64
maxNrOfPosSIBs								INTEGER ::= 32 
maxNoOfMeasTRPs								INTEGER ::= 64
maxnoTRPs									INTEGER ::= 65535
maxnoTRPInfoTypes							INTEGER ::= 64
maxnoofAngleInfo							INTEGER ::= 65535
maxnolcs-gcs-translation					INTEGER ::= 3
maxnoBcastCell								INTEGER ::= 16384
maxnoSRSTriggerStates						INTEGER ::= 3
maxnoSpatialRelations						INTEGER ::= 64
maxnoPosMeas								INTEGER ::= 16384
maxnoSRS-Carriers							INTEGER ::= 32
maxnoSCSs									INTEGER ::= 5
maxnoSRS-Resources							INTEGER ::= 64
maxnoSRS-PosResources						INTEGER ::= 64
maxnoSRS-ResourceSets						INTEGER ::= 16
maxnoSRS-ResourcePerSet						INTEGER ::= 16
maxnoSRS-PosResourceSets					INTEGER ::= 16
maxnoSRS-PosResourcePerSet					INTEGER ::= 16
maxPRS-ResourceSets							INTEGER ::= 2
maxPRS-ResourcesPerSet						INTEGER ::= 64
maxNoSSBs									INTEGER ::= 255
maxnoofPRSresourceSet						INTEGER ::= 8
maxnoofPRSresource							INTEGER ::= 64
maxnoofULAoAs								INTEGER ::= 8
maxNoPathExtended							INTEGER ::= 8
maxnoARPs									INTEGER ::=	16
maxnoUETEGs									INTEGER ::= 256
maxnoTRPTEGs								INTEGER ::= 8
maxFreqLayers								INTEGER ::= 4
maxNumResourcesPerAngle						INTEGER ::= 24
maxnoAzimuthAngles							INTEGER ::= 3600
maxnoElevationAngles						INTEGER ::= 1801
maxnoPRSTRPs								INTEGER ::= 256
maxnoVACell									INTEGER ::= 32
maxnoaggregatedPosSRS-Resources				INTEGER ::= 3
maxnoaggregatedPosSRS-ResourceSets			INTEGER ::= 3
maxnoAggPosPRSResourceSets					INTEGER ::= 3
maxnoofTimeWindowSRS						INTEGER ::= 16
maxnoofTimeWindowMeas						INTEGER ::= 16
maxnoPreconfiguredSRS						INTEGER ::= 16
maxnoofHopsMinusOne							INTEGER ::= 5
maxnoAggCombinations						INTEGER ::= 2
maxnoAggregatedPosSRSCombinations			INTEGER ::= 32
maxnoofChannelRes							INTEGER ::= 24

																								

-- **************************************************************
--
-- IEs
--
-- **************************************************************

id-Cause														ProtocolIE-ID ::= 0
id-CriticalityDiagnostics										ProtocolIE-ID ::= 1
id-LMF-UE-Measurement-ID										ProtocolIE-ID ::= 2
id-ReportCharacteristics										ProtocolIE-ID ::= 3
id-MeasurementPeriodicity										ProtocolIE-ID ::= 4
id-MeasurementQuantities										ProtocolIE-ID ::= 5
id-RAN-UE-Measurement-ID										ProtocolIE-ID ::= 6
id-E-CID-MeasurementResult										ProtocolIE-ID ::= 7
id-OTDOACells													ProtocolIE-ID ::= 8
id-OTDOA-Information-Type-Group									ProtocolIE-ID ::= 9
id-OTDOA-Information-Type-Item									ProtocolIE-ID ::= 10
id-MeasurementQuantities-Item									ProtocolIE-ID ::= 11
id-RequestedSRSTransmissionCharacteristics						ProtocolIE-ID ::= 12
id-Cell-Portion-ID												ProtocolIE-ID ::= 14
id-OtherRATMeasurementQuantities								ProtocolIE-ID ::= 15
id-OtherRATMeasurementQuantities-Item							ProtocolIE-ID ::= 16
id-OtherRATMeasurementResult									ProtocolIE-ID ::= 17
id-WLANMeasurementQuantities									ProtocolIE-ID ::= 19
id-WLANMeasurementQuantities-Item								ProtocolIE-ID ::= 20
id-WLANMeasurementResult										ProtocolIE-ID ::= 21
id-TDD-Config-EUTRA-Item										ProtocolIE-ID ::= 22
id-Assistance-Information										ProtocolIE-ID ::= 23
id-Broadcast													ProtocolIE-ID ::= 24
id-AssistanceInformationFailureList								ProtocolIE-ID ::= 25
id-SRSConfiguration												ProtocolIE-ID ::= 26
id-MeasurementResult											ProtocolIE-ID ::= 27
id-TRP-ID														ProtocolIE-ID ::= 28
	id-TRPInformationTypeListTRPReq									ProtocolIE-ID ::= 29
	id-TRPInformationListTRPResp									ProtocolIE-ID ::= 30
	id-MeasurementBeamInfoRequest									ProtocolIE-ID ::= 31
id-ResultSS-RSRP												ProtocolIE-ID ::= 32
id-ResultSS-RSRQ												ProtocolIE-ID ::= 33
id-ResultCSI-RSRP												ProtocolIE-ID ::= 34
id-ResultCSI-RSRQ												ProtocolIE-ID ::= 35
id-AngleOfArrivalNR												ProtocolIE-ID ::= 36
id-GeographicalCoordinates										ProtocolIE-ID ::= 37
id-PositioningBroadcastCells									ProtocolIE-ID ::= 38
id-LMF-Measurement-ID											ProtocolIE-ID ::= 39
id-RAN-Measurement-ID											ProtocolIE-ID ::= 40
	id-TRP-MeasurementRequestList									ProtocolIE-ID ::= 41
	id-TRP-MeasurementResponseList									ProtocolIE-ID ::= 42
	id-TRP-MeasurementReportList									ProtocolIE-ID ::= 43
	id-SRSType														ProtocolIE-ID ::= 44
	id-ActivationTime												ProtocolIE-ID ::= 45
id-SRSResourceSetID												ProtocolIE-ID ::= 46
id-TRPList														ProtocolIE-ID ::= 47
id-SRSSpatialRelation											ProtocolIE-ID ::= 48
id-SystemFrameNumber											ProtocolIE-ID ::= 49
id-SlotNumber													ProtocolIE-ID ::= 50
id-SRSResourceTrigger											ProtocolIE-ID ::= 51
id-TRPMeasurementQuantities										ProtocolIE-ID ::= 52
id-AbortTransmission											ProtocolIE-ID ::= 53
id-SFNInitialisationTime										ProtocolIE-ID ::= 54
id-ResultNR														ProtocolIE-ID ::= 55
id-ResultEUTRA													ProtocolIE-ID ::= 56
id-TRPInformationTypeItem										ProtocolIE-ID ::= 57
id-CGI-NR														ProtocolIE-ID ::= 58
id-SFNInitialisationTime-NR										ProtocolIE-ID ::= 59
id-Cell-ID														ProtocolIE-ID ::= 60
id-SrsFrequency													ProtocolIE-ID ::= 61
id-TRPType														ProtocolIE-ID ::= 62
id-SRSSpatialRelationPerSRSResource								ProtocolIE-ID ::= 63
id-MeasurementPeriodicityExtended								ProtocolIE-ID ::= 64
id-PRS-Resource-ID												ProtocolIE-ID ::= 65
id-PRSTRPList													ProtocolIE-ID ::= 66
id-PRSTransmissionTRPList										ProtocolIE-ID ::= 67
id-OnDemandPRS													ProtocolIE-ID ::= 68
id-AoA-SearchWindow												ProtocolIE-ID ::= 69
id-TRP-MeasurementUpdateList									ProtocolIE-ID ::= 70
id-ZoA															ProtocolIE-ID ::= 71
id-ResponseTime													ProtocolIE-ID ::= 72
id-UEReportingInformation										ProtocolIE-ID ::= 73
id-MultipleULAoA												ProtocolIE-ID ::= 74
id-UL-SRS-RSRPP													ProtocolIE-ID ::= 75
id-SRSResourcetype												ProtocolIE-ID ::= 76
id-ExtendedAdditionalPathList									ProtocolIE-ID ::= 77
id-ARPLocationInfo												ProtocolIE-ID ::= 78
id-ARP-ID														ProtocolIE-ID ::= 79
id-LoS-NLoSInformation											ProtocolIE-ID ::= 80
id-UETxTEGAssociationList										ProtocolIE-ID ::= 81
id-NumberOfTRPRxTEG												ProtocolIE-ID ::= 82
id-NumberOfTRPRxTxTEG											ProtocolIE-ID ::= 83
id-TRPTxTEGAssociation											ProtocolIE-ID ::= 84
id-TRPTEGInformation											ProtocolIE-ID ::= 85
id-TRP-Rx-TEGInformation										ProtocolIE-ID ::= 86
id-TRP-PRS-Information-List										ProtocolIE-ID ::= 87
id-PRS-Measurements-Info-List									ProtocolIE-ID ::= 88
id-PRSConfigRequestType											ProtocolIE-ID ::= 89
id-UE-TEG-Info-Request											ProtocolIE-ID ::= 90
id-MeasurementTimeOccasion										ProtocolIE-ID ::= 91
id-MeasurementCharacteristicsRequestIndicator					ProtocolIE-ID ::= 92
id-TRPBeamAntennaInformation									ProtocolIE-ID ::= 93
id-NR-TADV														ProtocolIE-ID ::= 94
id-MeasurementAmount											ProtocolIE-ID ::= 95
id-pathPower													ProtocolIE-ID ::= 96
id-PreconfigurationResult										ProtocolIE-ID ::= 97
id-RequestType													ProtocolIE-ID ::= 98
id-UE-TEG-ReportingPeriodicity									ProtocolIE-ID ::= 99
id-SRSPortIndex													ProtocolIE-ID ::= 100
	id-procedure-code-101-not-to-be-used							ProtocolIE-ID ::= 101
	id-procedure-code-102-not-to-be-used							ProtocolIE-ID ::= 102
	id-procedure-code-103-not-to-be-used							ProtocolIE-ID ::= 103
	id-UETxTimingErrorMargin										ProtocolIE-ID ::= 104
id-MeasurementPeriodicityNR-AoA									ProtocolIE-ID ::= 105
id-SRSTransmissionStatus										ProtocolIE-ID ::= 106
	id-nrofSymbolsExtended											ProtocolIE-ID ::= 107
id-repetitionFactorExtended										ProtocolIE-ID ::= 108
id-StartRBHopping												ProtocolIE-ID ::= 109
id-StartRBIndex													ProtocolIE-ID ::= 110
id-transmissionCombn8											ProtocolIE-ID ::= 111
id-ExtendedResourceSymbolOffset									ProtocolIE-ID ::= 112
id-NewNRCGI														ProtocolIE-ID ::= 113
id-Mobile-TRP-LocationInformation								ProtocolIE-ID ::= 114
id-Mobile-IAB-MT-UE-ID											ProtocolIE-ID ::= 115
id-MobileAccessPointLocation									ProtocolIE-ID ::= 116
id-CommonTAParameters											ProtocolIE-ID ::= 117
id-UE-Rx-Tx-Time-Diff											ProtocolIE-ID ::= 118
id-SCS-480														ProtocolIE-ID ::= 119
id-SCS-960														ProtocolIE-ID ::= 120
id-Bandwidth-Aggregation-Request-Indication						ProtocolIE-ID ::= 121
id-PosSRSResourceSet-Aggregation-List							ProtocolIE-ID ::= 122
id-TimingReportingGranularityFactorExtended						ProtocolIE-ID ::= 123
id-TimeWindowInformation-SRS-List								ProtocolIE-ID ::= 124
id-TimeWindowInformation-Measurement-List						ProtocolIE-ID ::= 125
id-UL-RSCPMeas													ProtocolIE-ID ::= 126
id-SymbolIndex													ProtocolIE-ID ::= 127
id-PosValidityAreaCellList 										ProtocolIE-ID ::= 128
id-SRSReservationType											ProtocolIE-ID ::= 129
id-PRSBWAggregationRequestInfoList								ProtocolIE-ID ::= 130
id-AggregatedPosSRSResourceID-List								ProtocolIE-ID ::= 131
id-AggregatedPRSResourceSetList									ProtocolIE-ID ::= 132
id-TRPPhaseQuality												ProtocolIE-ID ::= 133
id-NewCellIdentity												ProtocolIE-ID ::= 134
id-ValidityAreaSpecificSRSInformation							ProtocolIE-ID ::= 135
id-RequestedSRSPreconfigurationCharacteristics-List				ProtocolIE-ID ::= 136
id-SRSPreconfiguration-List										ProtocolIE-ID ::= 137
id-SRSInformation												ProtocolIE-ID ::= 138
id-TxHoppingConfiguration										ProtocolIE-ID ::= 139
id-MeasuredFrequencyHops										ProtocolIE-ID ::= 140
id-ReportingGranularitykminus1									ProtocolIE-ID ::= 141
id-ReportingGranularitykminus2									ProtocolIE-ID ::= 142
id-ReportingGranularitykminus3									ProtocolIE-ID ::= 143
id-ReportingGranularitykminus4									ProtocolIE-ID ::= 144
id-ReportingGranularitykminus5									ProtocolIE-ID ::= 145
id-ReportingGranularitykminus6									ProtocolIE-ID ::= 146
id-ReportingGranularitykminus1AdditionalPath					ProtocolIE-ID ::= 147
id-ReportingGranularitykminus2AdditionalPath					ProtocolIE-ID ::= 148
id-ReportingGranularitykminus3AdditionalPath					ProtocolIE-ID ::= 149
id-ReportingGranularitykminus4AdditionalPath					ProtocolIE-ID ::= 150
id-ReportingGranularitykminus5AdditionalPath					ProtocolIE-ID ::= 151
id-ReportingGranularitykminus6AdditionalPath					ProtocolIE-ID ::= 152
id-MeasuredResultsAssociatedInfoList							ProtocolIE-ID ::= 153
id-PointA														ProtocolIE-ID ::= 154
	id-NR-PCI														ProtocolIE-ID ::= 155
id-SCS-SpecificCarrier											ProtocolIE-ID ::= 156
id-MeasBasedOnAggregatedResources								ProtocolIE-ID ::= 157
id-UEReportingInterval-milliseconds								ProtocolIE-ID ::= 158
id-Remote-UE-Indication-Request									ProtocolIE-ID ::= 159
id-Remote-UE-Indication											ProtocolIE-ID ::= 160
id-Remote-UE-Status												ProtocolIE-ID ::= 161
id-LocalOrigin													ProtocolIE-ID ::= 162
id-PreconfiguredSRSInformation									ProtocolIE-ID ::= 163
id-DL-reference-signal-UERxTx-TD								ProtocolIE-ID ::= 164
id-SRSPosPeriodicConfigHyperSFNIndex							ProtocolIE-ID ::= 165
id-ValidityAreaSpecificSRSInformationExtended					ProtocolIE-ID ::= 166
id-E-CID-AoA-NR-per-TRP											ProtocolIE-ID ::= 167
id-WAB-MT-UE-ID													ProtocolIE-ID ::= 168
id-ChannelResponseInformation									ProtocolIE-ID ::= 169
id-UL-SRS-TDCT													ProtocolIE-ID ::= 170
id-PositioningDataInformation									ProtocolIE-ID ::= 171
id-PositioningDataUnavailable									ProtocolIE-ID ::= 172
id-PositioningDataCollectionNeeded								ProtocolIE-ID ::= 173
id-Inferred-measurement											ProtocolIE-ID ::= 174




END

-- **************************************************************
--
-- Container definitions
--
-- **************************************************************

NRPPA-Containers {
itu-t (0) identified-organization (4) etsi (0) mobileDomain (0) 
ngran-access (22) modules (3) nrppa (4) version1 (1) nrppa-Containers (5)}

DEFINITIONS AUTOMATIC TAGS ::= 

BEGIN

-- **************************************************************
--
-- IE parameter types from other modules.
--
-- **************************************************************

IMPORTS
	maxPrivateIEs,
	maxProtocolExtensions,
	maxProtocolIEs,
	Criticality,
	Presence,
	PrivateIE-ID,
	ProtocolIE-ID	
FROM NRPPA-CommonDataTypes;

-- **************************************************************
--
-- Class Definition for Protocol IEs
--
-- **************************************************************

NRPPA-PROTOCOL-IES ::= CLASS {
	&id					ProtocolIE-ID			UNIQUE,
	&criticality		Criticality,
	&Value,
	&presence			Presence
}
WITH SYNTAX {
	ID					&id
	CRITICALITY			&criticality
	TYPE				&Value
	PRESENCE			&presence
}

-- **************************************************************
--
-- Class Definition for Protocol Extensions
--
-- **************************************************************

NRPPA-PROTOCOL-EXTENSION ::= CLASS {
	&id					ProtocolIE-ID		UNIQUE,
	&criticality		Criticality,
	&Extension,
	&presence			Presence
}
WITH SYNTAX {
	ID					&id
	CRITICALITY			&criticality
	EXTENSION			&Extension
	PRESENCE			&presence
}

-- **************************************************************
--
-- Class Definition for Private IEs
--
-- **************************************************************

NRPPA-PRIVATE-IES ::= CLASS {
	&id					PrivateIE-ID,
	&criticality		Criticality,
	&Value,
	&presence			Presence
}
WITH SYNTAX {
	ID					&id
	CRITICALITY			&criticality
	TYPE				&Value
	PRESENCE			&presence
}

-- **************************************************************
--
-- Container for Protocol IEs
--
-- **************************************************************

ProtocolIE-Container { NRPPA-PROTOCOL-IES : IEsSetParam} ::= 
	SEQUENCE (SIZE (0..maxProtocolIEs)) OF
	ProtocolIE-Field {{IEsSetParam}}

ProtocolIE-Single-Container { NRPPA-PROTOCOL-IES : IEsSetParam} ::= 
	ProtocolIE-Field {{IEsSetParam}}

ProtocolIE-Field { NRPPA-PROTOCOL-IES : IEsSetParam} ::= SEQUENCE {
	id				NRPPA-PROTOCOL-IES.&id				({IEsSetParam}),
	criticality		NRPPA-PROTOCOL-IES.&criticality		({IEsSetParam}{@id}),
	value			NRPPA-PROTOCOL-IES.&Value			({IEsSetParam}{@id})
}

-- **************************************************************
--
-- Container Lists for Protocol IE Containers
--
-- **************************************************************

ProtocolIE-ContainerList {INTEGER : lowerBound, INTEGER : upperBound, NRPPA-PROTOCOL-IES : IEsSetParam} ::=
	SEQUENCE (SIZE (lowerBound..upperBound)) OF
	ProtocolIE-Container {{IEsSetParam}}

-- **************************************************************
--
-- Container for Protocol Extensions
--
-- **************************************************************

ProtocolExtensionContainer { NRPPA-PROTOCOL-EXTENSION : ExtensionSetParam} ::= 
	SEQUENCE (SIZE (1..maxProtocolExtensions)) OF
	ProtocolExtensionField {{ExtensionSetParam}}

ProtocolExtensionField { NRPPA-PROTOCOL-EXTENSION : ExtensionSetParam} ::= SEQUENCE {
	id					NRPPA-PROTOCOL-EXTENSION.&id			({ExtensionSetParam}),
	criticality			NRPPA-PROTOCOL-EXTENSION.&criticality	({ExtensionSetParam}{@id}),
	extensionValue		NRPPA-PROTOCOL-EXTENSION.&Extension		({ExtensionSetParam}{@id})
}

-- **************************************************************
--
-- Container for Private IEs
--
-- **************************************************************

PrivateIE-Container { NRPPA-PRIVATE-IES : IEsSetParam} ::= 
	SEQUENCE (SIZE (1..maxPrivateIEs)) OF
	PrivateIE-Field {{IEsSetParam}}

PrivateIE-Field { NRPPA-PRIVATE-IES : IEsSetParam} ::= SEQUENCE {
	id				NRPPA-PRIVATE-IES.&id				({IEsSetParam}),
	criticality		NRPPA-PRIVATE-IES.&criticality		({IEsSetParam}{@id}),
	value			NRPPA-PRIVATE-IES.&Value			({IEsSetParam}{@id})
}

END
